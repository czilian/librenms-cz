--
-- sntp.mib
-- MIB generated by MG-SOFT Visual MIB Builder Version 4.0 Build 349
-- Saturday, March 05, 2011 at 16:07:11
--

	SNTP-MIB DEFINITIONS ::= BEGIN
 
		IMPORTS
			Integer32, Unsigned32, Counter64, OBJECT-TYPE			
				FROM SNMPv2-SMI	
			wriProtocol			
				FROM WRI-SMI;
	
	
--
-- Node definitions
--
	
		-- 1.3.6.1.4.1.3807.2.1910
		sntp OBJECT IDENTIFIER ::= { wriProtocol 1910 }

		
		-- 1.3.6.1.4.1.3807.2.1910.1
		sntpCommon OBJECT IDENTIFIER ::= { sntp 1 }

		
		-- 1.3.6.1.4.1.3807.2.1910.1.1
		sntpClientSendInterval OBJECT-TYPE
			SYNTAX INTEGER (4..17)
			MAX-ACCESS read-write
			STATUS current
			DESCRIPTION
				"Client update interval, the value is the power of 2 second."
			::= { sntpCommon 1 }

		
		-- 1.3.6.1.4.1.3807.2.1910.1.2
		sntpServerSendInterval OBJECT-TYPE
			SYNTAX INTEGER (4..17)
			MAX-ACCESS read-write
			STATUS current
			DESCRIPTION
				"Server broadcast interval, the value is the power of 2 second."
			::= { sntpCommon 2 }

		
		-- 1.3.6.1.4.1.3807.2.1910.1.3
		sntpStratum OBJECT-TYPE
			SYNTAX INTEGER (0..16)
			MAX-ACCESS read-write
			STATUS current
			DESCRIPTION
				"Stratum value"
			::= { sntpCommon 3 }

		
		-- 1.3.6.1.4.1.3807.2.1910.1.4
		sntpMaster OBJECT-TYPE
			SYNTAX INTEGER
				{
				false(0),
				true(1)
				}
			MAX-ACCESS read-write
			STATUS current
			DESCRIPTION
				"If set true, device will be master."
			::= { sntpCommon 4 }

		
		-- 1.3.6.1.4.1.3807.2.1910.1.5
		sntpGlobalKeyId OBJECT-TYPE
			SYNTAX INTEGER
			MAX-ACCESS read-write
			STATUS current
			DESCRIPTION
				"Description."
			::= { sntpCommon 5 }

		
		-- 1.3.6.1.4.1.3807.2.1910.1.6
		sntpKeyGlobalStatus OBJECT-TYPE
			SYNTAX Integer32
			MAX-ACCESS read-write
			STATUS current
			DESCRIPTION
				"Authentication status. 
				enable(1), 
				disable(2)"
			::= { sntpCommon 6 }

		
		-- 1.3.6.1.4.1.3807.2.1910.1.7
		sntpKeyIdFreeIndex OBJECT-TYPE
			SYNTAX Integer32
			MAX-ACCESS read-only
			STATUS current
			DESCRIPTION
				"Description."
			::= { sntpCommon 7 }

		
		-- 1.3.6.1.4.1.3807.2.1910.1.8
		sntpPeerFreeIndex OBJECT-TYPE
			SYNTAX Integer32
			MAX-ACCESS read-only
			STATUS current
			DESCRIPTION
				"Peer free index. The value can be used as the index of sntpPeerEntry."
			::= { sntpCommon 8 }

		
		-- 1.3.6.1.4.1.3807.2.1910.2
		sntpKeyTable OBJECT-TYPE
			SYNTAX SEQUENCE OF SntpKeyEntry
			MAX-ACCESS not-accessible
			STATUS current
			DESCRIPTION
				"Description."
			::= { sntp 2 }

		
		-- 1.3.6.1.4.1.3807.2.1910.2.1
		sntpKeyEntry OBJECT-TYPE
			SYNTAX SntpKeyEntry
			MAX-ACCESS not-accessible
			STATUS current
			DESCRIPTION
				"Description."
			INDEX { sntpKeyId }
			::= { sntpKeyTable 1 }

		
		SntpKeyEntry ::=
			SEQUENCE { 
				sntpKeyId
					Unsigned32,
				sntpKeyString
					OCTET STRING,
				sntpKeyIdTrust
					INTEGER,
				sntpKeyEntryStatus
					Integer32
			 }

		-- 1.3.6.1.4.1.3807.2.1910.2.1.1
		sntpKeyId OBJECT-TYPE
			SYNTAX Unsigned32
			MAX-ACCESS read-only
			STATUS current
			DESCRIPTION
				"Index."
			::= { sntpKeyEntry 1 }

		
		-- 1.3.6.1.4.1.3807.2.1910.2.1.2
		sntpKeyString OBJECT-TYPE
			SYNTAX OCTET STRING
			MAX-ACCESS read-write
			STATUS current
			DESCRIPTION
				"Md5 key string."
			::= { sntpKeyEntry 2 }

		
		-- 1.3.6.1.4.1.3807.2.1910.2.1.3
		sntpKeyIdTrust OBJECT-TYPE
			SYNTAX INTEGER
				{
				true(1),
				false(2)
				}
			MAX-ACCESS read-write
			STATUS current
			DESCRIPTION
				"Set the key id to be trust or not."
			::= { sntpKeyEntry 3 }

		
		-- 1.3.6.1.4.1.3807.2.1910.2.1.4
		sntpKeyEntryStatus OBJECT-TYPE
			SYNTAX Integer32
			MAX-ACCESS read-write
			STATUS current
			DESCRIPTION
				"Sntp key entry status. 
				valid(1),
 				createRequest(2),
 				underCreation(3),
 				invalid(4)"
			::= { sntpKeyEntry 4 }

		
		-- 1.3.6.1.4.1.3807.2.1910.3
		sntpPeerTable OBJECT-TYPE
			SYNTAX SEQUENCE OF SntpPeerEntry
			MAX-ACCESS not-accessible
			STATUS current
			DESCRIPTION
				"Description."
			::= { sntp 3 }

		
		-- 1.3.6.1.4.1.3807.2.1910.3.1
		sntpPeerEntry OBJECT-TYPE
			SYNTAX SntpPeerEntry
			MAX-ACCESS not-accessible
			STATUS current
			DESCRIPTION
				"Description."
			INDEX { sntpPeerIndex }
			::= { sntpPeerTable 1 }

		
		SntpPeerEntry ::=
			SEQUENCE { 
				sntpPeerIndex
					Integer32,
				sntpPeerWorkMode
					Integer32,
				sntpPeerFamily
					Integer32,
				sntpPeerHostIp
					OCTET STRING,
				sntpPeerPeerIp
					OCTET STRING,
				sntpPeerVersion
					Integer32,
				sntpPeerKeyId
					Unsigned32,
				sntpPeerPort
					Integer32,
				sntpPeerEntryStatus
					Integer32,
				sntpPeerReferenceClock
					OCTET STRING,
				sntpPeerClockState
					INTEGER,
				sntpPeerClockOffset
					Counter64,
				sntpPeerClockDelay
					Counter64,
				sntpPeerPrecison
					INTEGER,
				sntpPeerReferTime
					Counter64,
				sntpPeerOrgTime
					Counter64,
				sntpPeerRcvTime
					Counter64,
				sntpPeerXmtTime
					Counter64,
				sntpPeerRootDelay
					Counter64,
				sntpPeerPeerWorkMode
					INTEGER,
				sntpPeerSourceIP
					OCTET STRING
			 }

		-- 1.3.6.1.4.1.3807.2.1910.3.1.1
		sntpPeerIndex OBJECT-TYPE
			SYNTAX Integer32
			MAX-ACCESS read-only
			STATUS current
			DESCRIPTION
				"Description."
			::= { sntpPeerEntry 1 }

		
		-- 1.3.6.1.4.1.3807.2.1910.3.1.2
		sntpPeerWorkMode OBJECT-TYPE
			SYNTAX Integer32
			MAX-ACCESS read-write
			STATUS current
			DESCRIPTION
				"Work mode.
				SNTP_UNSPETIC 0
				SNTP_PEER_ACTIVE 1
				SNTP_PEER_PASSIVE 2
				SNTP_UNICAST_CLIENT 3
				SNTP_UNICAST_SERVER 4
				SNTP_BROADCAST_SERVER 5
				SNTP_MANYCAST_CLIENT 7
				SNTP_BROADCAST_CLIENT 8
				SNTP_MANYCAST_SERVER 9"
			::= { sntpPeerEntry 2 }

		
		-- 1.3.6.1.4.1.3807.2.1910.3.1.3
		sntpPeerFamily OBJECT-TYPE
			SYNTAX Integer32
			MAX-ACCESS read-write
			STATUS current
			DESCRIPTION
				"IP address type.
				 ipv4(1), 
				 ipv6(2)"
			::= { sntpPeerEntry 3 }

		
		-- 1.3.6.1.4.1.3807.2.1910.3.1.4
		sntpPeerHostIp OBJECT-TYPE
			SYNTAX OCTET STRING (SIZE (0..16))
			MAX-ACCESS read-write
			STATUS current
			DESCRIPTION
				"Local host ip address."
			::= { sntpPeerEntry 4 }

		
		-- 1.3.6.1.4.1.3807.2.1910.3.1.5
		sntpPeerPeerIp OBJECT-TYPE
			SYNTAX OCTET STRING (SIZE (0..16))
			MAX-ACCESS read-write
			STATUS current
			DESCRIPTION
				"Peer ip address."
			::= { sntpPeerEntry 5 }

		
		-- 1.3.6.1.4.1.3807.2.1910.3.1.6
		sntpPeerVersion OBJECT-TYPE
			SYNTAX Integer32
			MAX-ACCESS read-write
			STATUS current
			DESCRIPTION
				"Peer version."
			::= { sntpPeerEntry 6 }

		
		-- 1.3.6.1.4.1.3807.2.1910.3.1.7
		sntpPeerKeyId OBJECT-TYPE
			SYNTAX Unsigned32
			MAX-ACCESS read-write
			STATUS current
			DESCRIPTION
				"Peer authentication keyid."
			::= { sntpPeerEntry 7 }

		
		-- 1.3.6.1.4.1.3807.2.1910.3.1.8
		sntpPeerPort OBJECT-TYPE
			SYNTAX Integer32
			MAX-ACCESS read-only
			STATUS current
			DESCRIPTION
				"Peer port."
			::= { sntpPeerEntry 8 }

		
		-- 1.3.6.1.4.1.3807.2.1910.3.1.9
		sntpPeerEntryStatus OBJECT-TYPE
			SYNTAX Integer32
			MAX-ACCESS read-write
			STATUS current
			DESCRIPTION
				"Sntp peer entry status.
				valid(1),
 				createRequest(2),
 				underCreation(3),
 				invalid(4)"				
			::= { sntpPeerEntry 9 }

		
		-- 1.3.6.1.4.1.3807.2.1910.3.1.10
		sntpPeerReferenceClock OBJECT-TYPE
			SYNTAX OCTET STRING
			MAX-ACCESS read-only
			STATUS current
			DESCRIPTION
				"Peer reference clock."
			::= { sntpPeerEntry 10 }

		
		-- 1.3.6.1.4.1.3807.2.1910.3.1.11
		sntpPeerClockState OBJECT-TYPE
			SYNTAX INTEGER
			MAX-ACCESS read-only
			STATUS current
			DESCRIPTION
				"Peer clock state."
			::= { sntpPeerEntry 11 }

		
		-- 1.3.6.1.4.1.3807.2.1910.3.1.12
		sntpPeerClockOffset OBJECT-TYPE
			SYNTAX Counter64
			MAX-ACCESS read-only
			STATUS current
			DESCRIPTION
				"Peer clock offset."
			::= { sntpPeerEntry 12 }

		
		-- 1.3.6.1.4.1.3807.2.1910.3.1.13
		sntpPeerClockDelay OBJECT-TYPE
			SYNTAX Counter64
			MAX-ACCESS read-only
			STATUS current
			DESCRIPTION
				"Peer clock delay."
			::= { sntpPeerEntry 13 }

		
		-- 1.3.6.1.4.1.3807.2.1910.3.1.14
		sntpPeerPrecison OBJECT-TYPE
			SYNTAX INTEGER
			MAX-ACCESS read-only
			STATUS current
			DESCRIPTION
				"Peer precision."
			::= { sntpPeerEntry 14 }

		
		-- 1.3.6.1.4.1.3807.2.1910.3.1.15
		sntpPeerReferTime OBJECT-TYPE
			SYNTAX Counter64
			MAX-ACCESS read-only
			STATUS current
			DESCRIPTION
				"Peer reference time."
			::= { sntpPeerEntry 15 }

		
		-- 1.3.6.1.4.1.3807.2.1910.3.1.16
		sntpPeerOrgTime OBJECT-TYPE
			SYNTAX Counter64
			MAX-ACCESS read-only
			STATUS current
			DESCRIPTION
				"Peer originate time."
			::= { sntpPeerEntry 16 }

		
		-- 1.3.6.1.4.1.3807.2.1910.3.1.17
		sntpPeerRcvTime OBJECT-TYPE
			SYNTAX Counter64
			MAX-ACCESS read-only
			STATUS current
			DESCRIPTION
				"Peer receive time."
			::= { sntpPeerEntry 17 }

		
		-- 1.3.6.1.4.1.3807.2.1910.3.1.18
		sntpPeerXmtTime OBJECT-TYPE
			SYNTAX Counter64
			MAX-ACCESS read-only
			STATUS current
			DESCRIPTION
				"Peer transmit time."
			::= { sntpPeerEntry 18 }

		
		-- 1.3.6.1.4.1.3807.2.1910.3.1.19
		sntpPeerRootDelay OBJECT-TYPE
			SYNTAX Counter64
			MAX-ACCESS read-only
			STATUS current
			DESCRIPTION
				"Peer root delay."
			::= { sntpPeerEntry 19 }

		
		-- 1.3.6.1.4.1.3807.2.1910.3.1.20
		sntpPeerPeerWorkMode OBJECT-TYPE
			SYNTAX INTEGER
			MAX-ACCESS read-only
			STATUS current
			DESCRIPTION
				"Peer work mode."
			::= { sntpPeerEntry 20 }

		
		-- 1.3.6.1.4.1.3807.2.1910.3.1.21
		sntpPeerSourceIP OBJECT-TYPE
			SYNTAX OCTET STRING
			MAX-ACCESS read-only
			STATUS current
			DESCRIPTION
				"Peer source ip address."
			::= { sntpPeerEntry 21 }

		
	
	END

--
-- sntp.mib
--
