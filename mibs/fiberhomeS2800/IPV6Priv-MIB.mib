IPV6Priv-MIB DEFINITIONS ::= BEGIN

         IMPORTS
             MODULE-IDENTITY, OBJECT-TYPE, NOTIFICATION-TYPE,
             mib-2, Counter32, Unsigned32, Integer32,
             Gauge32,enterprises                               FROM SNMPv2-SMI
             DisplayString, PhysAddress, TruthValue, TimeStamp,
             VariablePointer, RowPointer           FROM SNMPv2-TC
             MODULE-COMPLIANCE, OBJECT-GROUP,
             NOTIFICATION-GROUP                    FROM SNMPv2-CONF
             Ipv6IfIndex, Ipv6Address, Ipv6AddressPrefix,
             Ipv6AddressIfIdentifier,
             Ipv6IfIndexOrZero                     FROM IPV6-TC;
             
         wri MODULE-IDENTITY
							LAST-UPDATED 	"201107040000Z"
							ORGANIZATION 	"FiberHome Networks Systems, Inc."
							CONTACT-INFO	"http://www.fhn.com.cn"
							DESCRIPTION		"The Structure of Management Information for the FHN enterprise."
							::= { enterprises 3807 }	-- assigned by IANA
	
				wriProtocol           OBJECT IDENTIFIER ::= { wri 2 }
				wriIPv6               OBJECT IDENTIFIER ::= { wriProtocol 927 }

           
		-- the IPv6 general group
		

         ipv6PrivMIBObjects OBJECT IDENTIFIER   ::= { wriIPv6 1 }


         ipv6PrivForwarding OBJECT-TYPE
             SYNTAX      INTEGER {
                          forwarding(1),    -- acting as a router

                                            -- NOT acting as
                          notForwarding(2)  -- a router
                         }
              MAX-ACCESS read-write
              STATUS     current
              DESCRIPTION
                "The indication of whether this entity is acting
                as an IPv6 router in respect to the forwarding of
                datagrams received by, but not addressed to, this
                entity.  IPv6 routers forward datagrams.  IPv6
                hosts do not (except those source-routed via the
                host).
                Note that for some managed nodes, this object may
                take on only a subset of the values possible.
                Accordingly, it is appropriate for an agent to
                return a `wrongValue' response if a management
                station attempts to change this object to an
                inappropriate value."
                ::= { ipv6PrivMIBObjects 1 }

         ipv6PrivDefaultHopLimit OBJECT-TYPE
             SYNTAX      INTEGER(0..255)
             MAX-ACCESS  read-write
              STATUS     current
             DESCRIPTION
                "The default value inserted into the Hop Limit
                field of the IPv6 header of datagrams originated
                at this entity, whenever a Hop Limit value is not
                supplied by the transport layer protocol."
             DEFVAL  { 64 }
             ::= { ipv6PrivMIBObjects 2 }

        ipv6PrivInterfaces OBJECT-TYPE
             SYNTAX      Unsigned32
             MAX-ACCESS  read-only
             STATUS      current
             DESCRIPTION
               "The number of IPv6 interfaces (regardless of
                their current state) present on this system."
             ::= { ipv6PrivMIBObjects 3 }

        ipv6PrivIfTableLastChange OBJECT-TYPE
             SYNTAX      TimeStamp
             MAX-ACCESS  read-only
             STATUS      current
             DESCRIPTION
               "The value of sysUpTime at the time of the last
               insertion or removal of an entry in the
               ipv6PrivIfTable. If the number of entries has been
               unchanged since the last re-initialization of
               the local network management subsystem, then this
               object contains a zero value."
             ::= { ipv6PrivMIBObjects 4 }


        -- the IPv6 Interfaces table

        ipv6PrivIfTable OBJECT-TYPE
             SYNTAX     SEQUENCE OF Ipv6PrivIfEntry
             MAX-ACCESS not-accessible
             STATUS     current
             DESCRIPTION
               "The IPv6 Interfaces table contains information
               on the entity's internetwork-layer interfaces.
               An IPv6 interface constitutes a logical network
               layer attachment to the layer immediately below
               IPv6 including internet layer 'tunnels', such as
               tunnels over IPv4 or IPv6 itself."
             ::= { ipv6PrivMIBObjects 5 }

         ipv6PrivIfEntry OBJECT-TYPE
             SYNTAX     Ipv6PrivIfEntry
             MAX-ACCESS not-accessible
             STATUS     current
             DESCRIPTION
               "An interface entry containing objects
                about a particular IPv6 interface."
             INDEX   { ipv6PrivIfIndex }
             ::= { ipv6PrivIfTable 1 }

         Ipv6PrivIfEntry ::= SEQUENCE {
                 ipv6PrivIfIndex              Ipv6IfIndex,
                 ipv6PrivIfDescr              DisplayString,
                 ipv6PrivIfLowerLayer         VariablePointer,
                 ipv6PrivIfEffectiveMtu       Unsigned32,
                 ipv6PrivIfReasmMaxSize       Unsigned32,
                 ipv6PrivIfIdentifier         Ipv6AddressIfIdentifier,
                 ipv6PrivIfIdentifierLength   INTEGER,
                 ipv6PrivIfPhysicalAddress    PhysAddress,
                 ipv6PrivIfAdminStatus        INTEGER,
                 ipv6PrivIfOperStatus         INTEGER,
                 ipv6PrivIfLastChange         TimeStamp,
				 ipv6PrivIfStatus         	  INTEGER,
				 ipv6PrivIfAutoLinkLocal      INTEGER
             }

         ipv6PrivIfIndex OBJECT-TYPE
             SYNTAX     Ipv6IfIndex
             MAX-ACCESS read-only
             STATUS     current
             DESCRIPTION
               "A unique non-zero value identifying
                the particular IPv6 interface."
             ::= { ipv6PrivIfEntry 1 }

         ipv6PrivIfDescr OBJECT-TYPE
             SYNTAX     DisplayString
             MAX-ACCESS read-write
             STATUS     current
             DESCRIPTION
               "A textual string containing information about the
               interface.  This string may be set by the network
               management system."
             ::= { ipv6PrivIfEntry 2 }

         ipv6PrivIfLowerLayer OBJECT-TYPE
         SYNTAX      VariablePointer
            MAX-ACCESS  read-only
            STATUS      current
            DESCRIPTION
              "This object identifies the protocol layer over
               which this network interface operates.  If this
               network interface operates over the data-link
               layer, then the value of this object refers to an
               instance of ifIndex [6]. If this network interface
               operates over an IPv4 interface, the value of this
               object refers to an instance of ipAdEntAddr [3].

               If this network interface operates over another
               IPv6 interface, the value of this object refers to
               an instance of ipv6PrivIfIndex.  If this network
               interface is not currently operating over an active
               protocol layer, then the value of this object
               should be set to the OBJECT ID { 0 0 }."
            ::= { ipv6PrivIfEntry 3 }

         ipv6PrivIfEffectiveMtu OBJECT-TYPE
            SYNTAX      Unsigned32
            UNITS       "octets"
            MAX-ACCESS  read-write
            STATUS      current
            DESCRIPTION
              "The size of the largest IPv6 packet which can be
              sent/received on the interface, specified in
              octets."
         ::= { ipv6PrivIfEntry 4 }

         ipv6PrivIfReasmMaxSize OBJECT-TYPE
            SYNTAX      Unsigned32 (0..65535)
            UNITS       "octets"
            MAX-ACCESS  read-only
            STATUS      current
            DESCRIPTION
              "The size of the largest IPv6 datagram which this
              entity can re-assemble from incoming IPv6 fragmented
              datagrams received on this interface."
         ::= { ipv6PrivIfEntry 5 }

         ipv6PrivIfIdentifier OBJECT-TYPE
             SYNTAX      Ipv6AddressIfIdentifier
             MAX-ACCESS  read-write
             STATUS      current
             DESCRIPTION
                "The Interface Identifier for this interface that
                is (at least) unique on the link this interface is
                attached to. The Interface Identifier is combined
                with an address prefix to form an interface address.

                By default, the Interface Identifier is autoconfigured
                according to the rules of the link type this
                interface is attached to."
             ::= { ipv6PrivIfEntry 6 } 
             
         ipv6PrivIfIdentifierLength OBJECT-TYPE
             SYNTAX      INTEGER (0..64)
             UNITS       "bits"
             MAX-ACCESS  read-write
             STATUS      current
             DESCRIPTION
               "The length of the Interface Identifier in bits."
             ::= { ipv6PrivIfEntry 7 }

         ipv6PrivIfPhysicalAddress OBJECT-TYPE
             SYNTAX      PhysAddress
             MAX-ACCESS  read-only
             STATUS      current
             DESCRIPTION
               "The interface's physical address. For example, for
               an IPv6 interface attached to an 802.x link, this
               object normally contains a MAC address. Note that
               in some cases this address may differ from the
               address of the interface's protocol sub-layer.  The
               interface's media-specific MIB must define the bit
               and byte ordering and the format of the value of
               this object. For interfaces which do not have such
               an address (e.g., a serial line), this object should
               contain an octet string of zero length."
             ::= { ipv6PrivIfEntry 8 }

        ipv6PrivIfAdminStatus OBJECT-TYPE
            SYNTAX  INTEGER {
                     up(1),       -- ready to pass packets
                     down(2)
                    }
            MAX-ACCESS  read-write
            STATUS      current
            DESCRIPTION
              "The desired state of the interface.  When a managed
              system initializes,  all IPv6 interfaces start with
              ipv6PrivIfAdminStatus in the down(2) state.  As a result
              of either explicit management action or per
              configuration information retained by the managed
              system,  ipv6PrivIfAdminStatus is then changed to
              the up(1) state (or remains in the down(2) state)."
            ::= { ipv6PrivIfEntry 9 }

        ipv6PrivIfOperStatus OBJECT-TYPE
            SYNTAX  INTEGER {
                     up(1),             -- ready to pass packets

                     down(2),

                     noIfIdentifier(3), -- no interface identifier

                                        -- status can not be
                                        -- determined for some
                     unknown(4),        -- reason

                                        -- some component is
                     notPresent(5)      -- missing
                    }
            MAX-ACCESS  read-only
            STATUS      current
            DESCRIPTION
              "The current operational state of the interface.
              The noIfIdentifier(3) state indicates that no valid
              Interface Identifier is assigned to the interface.
              This state usually indicates that the link-local
              interface address failed Duplicate Address Detection.
              If ipv6PrivIfAdminStatus is down(2) then ipv6PrivIfOperStatus
              should be down(2).  If ipv6PrivIfAdminStatus is changed
              to up(1) then ipv6PrivIfOperStatus should change to up(1)
              if the interface is ready to transmit and receive
              network traffic; it should remain in the down(2) or
              noIfIdentifier(3) state if and only if there is a
              fault that prevents it from going to the up(1) state;
              it should remain in the notPresent(5) state if
              the interface has missing (typically, lower layer)
              components."
            ::= { ipv6PrivIfEntry 10 }

        ipv6PrivIfLastChange OBJECT-TYPE
            SYNTAX      TimeStamp
            MAX-ACCESS  read-only
            STATUS      current
            DESCRIPTION
                "The value of sysUpTime at the time the interface
                entered its current operational state.  If the
                current state was entered prior to the last
                re-initialization of the local network management
                subsystem, then this object contains a zero
                value."
            ::= { ipv6PrivIfEntry 11 }

		ipv6PrivIfStatus OBJECT-TYPE
            SYNTAX      INTEGER
			{
				 enable(1),             
                 disable(2)
			}
            MAX-ACCESS  read-write
            STATUS      current
            DESCRIPTION
                "The ipv6 status of interface."
            ::= { ipv6PrivIfEntry 12 }
			
		ipv6PrivIfAutoLinkLocal OBJECT-TYPE
            SYNTAX      INTEGER
			{
				 true(1),             
                 false(2)
			}
            MAX-ACCESS  read-write
            STATUS      current
            DESCRIPTION
                "The ipv6 status of link local."
            ::= { ipv6PrivIfEntry 13 }
			
         --  IPv6 Interface Statistics table

         ipv6PrivIfStatsTable OBJECT-TYPE
             SYNTAX     SEQUENCE OF Ipv6IfStatsEntry
             MAX-ACCESS not-accessible
             STATUS     current
             DESCRIPTION
                 "IPv6 interface traffic statistics."
             ::= { ipv6PrivMIBObjects 6 }

         ipv6PrivIfStatsEntry OBJECT-TYPE
             SYNTAX     Ipv6IfStatsEntry
             MAX-ACCESS not-accessible
             STATUS     current
             DESCRIPTION
                 "An interface statistics entry containing objects
                 at a particular IPv6 interface."
             AUGMENTS { ipv6PrivIfEntry }
             ::= { ipv6PrivIfStatsTable 1 }

         Ipv6IfStatsEntry ::= SEQUENCE {
                 ipv6PrivIfStatsInReceives
                     Counter32,
                 ipv6PrivIfStatsInHdrErrors
                     Counter32,
                 ipv6PrivIfStatsInTooBigErrors
                     Counter32,
                 ipv6PrivIfStatsInNoRoutes
                     Counter32,
                 ipv6PrivIfStatsInAddrErrors
                     Counter32,
                 ipv6PrivIfStatsInUnknownProtos
                     Counter32,
                 ipv6PrivIfStatsInTruncatedPkts
                     Counter32,
                 ipv6PrivIfStatsInDiscards
                     Counter32,
                 ipv6PrivIfStatsInDelivers
                     Counter32,
                 ipv6PrivIfStatsOutForwDatagrams
                     Counter32,
                 ipv6PrivIfStatsOutRequests
                     Counter32,
                 ipv6PrivIfStatsOutDiscards
                 Counter32,
                 ipv6PrivIfStatsOutFragOKs
                     Counter32,
                 ipv6PrivIfStatsOutFragFails
                     Counter32,
                 ipv6PrivIfStatsOutFragCreates
                     Counter32,
                 ipv6PrivIfStatsReasmReqds
                     Counter32,
                 ipv6PrivIfStatsReasmOKs
                     Counter32,
                 ipv6PrivIfStatsReasmFails
                     Counter32,
                 ipv6PrivIfStatsInMcastPkts
                     Counter32,
                 ipv6PrivIfStatsOutMcastPkts
                     Counter32,
           --private item
                 ipv6PrivIfStatsReset
                     INTEGER,                     
                 ipv6PrivIfStatsTcpInitiatedConns
                     Counter32,
                 ipv6PrivIfStatsTcpAcceptedConns
                     Counter32,
                 ipv6PrivIfStatsTcpEstablishedConns
                     Counter32,
                 ipv6PrivIfStatsTcpDroppedConns
                     Counter32,
                 ipv6PrivIfStatsTcpInitiatedDropConns
                     Counter32,
                 ipv6PrivIfStatsTcpClosedConns
                     Counter32,
                 ipv6PrivIfStatsTcpTimeoutDroppedConns
                     Counter32,
                 ipv6PrivIfStatsTcpRetransTimeout
                     Counter32,
                 ipv6PrivIfStatsTcpKeepAliveTimeout
                     Counter32,
                 ipv6PrivIfStatsTcpKeepAliveProbe
                     Counter32,
                 ipv6PrivIfStatsTcpDroppedInKeepalive
                     Counter32,
                 ipv6PrivIfStatsTcpInPackets
                 Counter32,
                 ipv6PrivIfStatsTcpInSequence
                     Counter32,
                 ipv6PrivIfStatsTcpInBytes
                     Counter32,
                 ipv6PrivIfStatsTcpInChecksumErrs
                     Counter32,
                 ipv6PrivIfStatsTcpInOffsetErrs
                     Counter32,
                 ipv6PrivIfStatsTcpInShortErrs
                     Counter32,
                 ipv6PrivIfStatsTcpInDuplicatePackets
                     Counter32,
                 ipv6PrivIfStatsTcpInDuplicateBytes
                     Counter32,
                 ipv6PrivIfStatsTcpInPartDuplicatePackets
                     Counter32,                     
                 ipv6PrivIfStatsTcpInPartDuplicateBytes
                     Counter32,
                 ipv6PrivIfStatsTcpInOutOrderPackets
                     Counter32,
                 ipv6PrivIfStatsTcpInOutOrderBytes
                     Counter32,
                 ipv6PrivIfStatsTcpInAfterWindowPackets
                     Counter32,
                 ipv6PrivIfStatsTcpInAfterWindowBytes
                     Counter32,
                 ipv6PrivIfStatsTcpInAfterClosePackets
                     Counter32,
                 ipv6PrivIfStatsTcpInWindowProbePacks
                     Counter32,
                 ipv6PrivIfStatsTcpInDuplicateAcks
                     Counter32,
                 ipv6PrivIfStatsTcpInTooMuchAcks
                     Counter32,
                 ipv6PrivIfStatsTcpInAckPackets
                     Counter32,
                 ipv6PrivIfStatsTcpInAckBytes
                     Counter32,
                 ipv6PrivIfStatsTcpInWindowUpdate
                 Counter32,
                 ipv6PrivIfStatsTcpOutDelayedAcks
                     Counter32,
                 ipv6PrivIfStatsTcpOutPackets
                     Counter32,
                 ipv6PrivIfStatsTcpOutDataPackets
                     Counter32,
                 ipv6PrivIfStatsTcpOutDataBytes
                     Counter32,
                 ipv6PrivIfStatsTcpOutRetransmitPackets
                     Counter32,
                 ipv6PrivIfStatsTcpOutRetransmitBytes
                     Counter32,
                 ipv6PrivIfStatsTcpOutAcks
                     Counter32,
                 ipv6PrivIfStatsTcpOutWindowProbes
                     Counter32,                     
                 ipv6PrivIfStatsTcpOutUrgentPackets
                     Counter32,
                 ipv6PrivIfStatsTcpOutWindowUpdates
                     Counter32,
                 ipv6PrivIfStatsTcpOutControls
                     Counter32,
                 ipv6PrivIfStatsTcpReset
                     INTEGER,
                 ipv6PrivIfStatsUdpInPackets
                     Counter32,
                 ipv6PrivIfStatsUdpInShorerThanHeaders
                     Counter32,
                 ipv6PrivIfStatsUdpInCheckError
                     Counter32,
                 ipv6PrivIfStatsUdpInInvalidLength
                     Counter32,
                 ipv6PrivIfStatsUdpInNoSocketOnPort
                     Counter32,                 
                 ipv6PrivIfStatsUdpInNoMulticastPort
                     Counter32,
                 ipv6PrivIfStatsUdpInSocketFull
                     Counter32,
                 ipv6PrivIfStatsUdpInPcbCacheMiss
                     Counter32,
                 ipv6PrivIfStatsUdpOutPackets
                     Counter32,
                 ipv6PrivIfStatsUdpReset
                     INTEGER
             }

         ipv6PrivIfStatsInReceives OBJECT-TYPE
             SYNTAX      Counter32
             MAX-ACCESS  read-only
             STATUS      current
             DESCRIPTION
                "The total number of input datagrams received by
                the interface, including those received in error."
             ::= { ipv6PrivIfStatsEntry 1 }

         ipv6PrivIfStatsInHdrErrors OBJECT-TYPE
             SYNTAX     Counter32
             MAX-ACCESS read-only
             STATUS     current
             DESCRIPTION
                "The number of input datagrams discarded due to
                errors in their IPv6 headers, including version
                number mismatch, other format errors, hop count
                exceeded, errors discovered in processing their
                IPv6 options, etc."
             ::= { ipv6PrivIfStatsEntry 2 }

         ipv6PrivIfStatsInTooBigErrors OBJECT-TYPE
             SYNTAX      Counter32
             MAX-ACCESS  read-only
             STATUS      current
             DESCRIPTION
               "The number of input datagrams that could not be
               forwarded because their size exceeded the link MTU
               of outgoing interface."
               ::= { ipv6PrivIfStatsEntry 3 }

         ipv6PrivIfStatsInNoRoutes OBJECT-TYPE
             SYNTAX      Counter32
             MAX-ACCESS  read-only
             STATUS      current
             DESCRIPTION
                "The number of input datagrams discarded because no
                 route could be found to transmit them to their
                 destination."
             ::= { ipv6PrivIfStatsEntry 4 }

         ipv6PrivIfStatsInAddrErrors OBJECT-TYPE
             SYNTAX      Counter32
             MAX-ACCESS  read-only
             STATUS      current
             DESCRIPTION
                "The number of input datagrams discarded because
                the IPv6 address in their IPv6 header's destination
                field was not a valid address to be received at
                this entity.  This count includes invalid
                addresses (e.g., ::0) and unsupported addresses
                (e.g., addresses with unallocated prefixes).  For
                entities which are not IPv6 routers and therefore
                do not forward datagrams, this counter includes
                datagrams discarded because the destination address
                was not a local address."
             ::= { ipv6PrivIfStatsEntry 5 }

         ipv6PrivIfStatsInUnknownProtos OBJECT-TYPE
             SYNTAX      Counter32
             MAX-ACCESS  read-only
             STATUS      current
             DESCRIPTION
                "The number of locally-addressed datagrams
                received successfully but discarded because of an
                unknown or unsupported protocol. This counter is
                incremented at the interface to which these
                datagrams were addressed which might not be
                necessarily the input interface for some of
                the datagrams."
             ::= { ipv6PrivIfStatsEntry 6 }


         ipv6PrivIfStatsInTruncatedPkts OBJECT-TYPE
             SYNTAX      Counter32
             MAX-ACCESS  read-only
             STATUS      current
             DESCRIPTION
                "The number of input datagrams discarded because
                 datagram frame didn't carry enough data."
             ::= { ipv6PrivIfStatsEntry 7 }

         ipv6PrivIfStatsInDiscards OBJECT-TYPE
             SYNTAX      Counter32
             MAX-ACCESS  read-only
             STATUS      current
             DESCRIPTION
                "The number of input IPv6 datagrams for which no
                problems were encountered to prevent their
                continued processing, but which were discarded
                (e.g., for lack of buffer space).  Note that this
                counter does not include any datagrams discarded
                while awaiting re-assembly."
             ::= { ipv6PrivIfStatsEntry 8 }

         ipv6PrivIfStatsInDelivers OBJECT-TYPE
             SYNTAX      Counter32
             MAX-ACCESS  read-only
             STATUS      current
             DESCRIPTION
              "The total number of datagrams successfully
              delivered to IPv6 user-protocols (including ICMP).
              This counter is incremented at the interface to
              which these datagrams were addressed which might
              not be necessarily the input interface for some of
              the datagrams."
             ::= { ipv6PrivIfStatsEntry 9 }

         ipv6PrivIfStatsOutForwDatagrams OBJECT-TYPE
             SYNTAX      Counter32
             MAX-ACCESS  read-only
             STATUS      current
             DESCRIPTION
                "The number of output datagrams which this
                entity received and forwarded to their final
                destinations.  In entities which do not act
                as IPv6 routers, this counter will include
                only those packets which were Source-Routed
                via this entity, and the Source-Route
                processing was successful.  Note that for
                a successfully forwarded datagram the counter
                of the outgoing interface is incremented."
             ::= { ipv6PrivIfStatsEntry 10 }

         ipv6PrivIfStatsOutRequests OBJECT-TYPE
         	 SYNTAX      Counter32
             MAX-ACCESS  read-only
             STATUS      current
             DESCRIPTION
              "The total number of IPv6 datagrams which local IPv6
              user-protocols (including ICMP) supplied to IPv6 in
              requests for transmission.  Note that this counter
              does not include any datagrams counted in
              ipv6PrivIfStatsOutForwDatagrams."
             ::= { ipv6PrivIfStatsEntry 11 }

         ipv6PrivIfStatsOutDiscards OBJECT-TYPE
             SYNTAX      Counter32
             MAX-ACCESS  read-only
             STATUS      current
             DESCRIPTION
                 "The number of output IPv6 datagrams for which no
                 problem was encountered to prevent their
                 transmission to their destination, but which were
                 discarded (e.g., for lack of buffer space).  Note
                 that this counter would include datagrams counted
                 in ipv6PrivIfStatsOutForwDatagrams if any such packets
                 met this (discretionary) discard criterion."
             ::= { ipv6PrivIfStatsEntry 12 }

         ipv6PrivIfStatsOutFragOKs OBJECT-TYPE
             SYNTAX      Counter32
             MAX-ACCESS  read-only
             STATUS      current
             DESCRIPTION
                "The number of IPv6 datagrams that have been
                 successfully fragmented at this output interface."
             ::= { ipv6PrivIfStatsEntry 13 }

         ipv6PrivIfStatsOutFragFails OBJECT-TYPE
             SYNTAX      Counter32
             MAX-ACCESS  read-only
             STATUS      current
             DESCRIPTION
                "The number of IPv6 datagrams that have been
                 discarded because they needed to be fragmented
                 at this output interface but could not be."
             ::= { ipv6PrivIfStatsEntry 14 }

         ipv6PrivIfStatsOutFragCreates OBJECT-TYPE
             SYNTAX      Counter32
             MAX-ACCESS  read-only
             STATUS      current
             DESCRIPTION
                "The number of output datagram fragments that have
                 been generated as a result of fragmentation at
                 this output interface."
             ::= { ipv6PrivIfStatsEntry 15 }

         ipv6PrivIfStatsReasmReqds OBJECT-TYPE
             SYNTAX      Counter32
             MAX-ACCESS  read-only
             STATUS      current
             DESCRIPTION
                "The number of IPv6 fragments received which needed
                 to be reassembled at this interface.  Note that this
                 counter is incremented at the interface to which
                 these fragments were addressed which might not
                 be necessarily the input interface for some of
                 the fragments."
             ::= { ipv6PrivIfStatsEntry 16 }

         ipv6PrivIfStatsReasmOKs OBJECT-TYPE
             SYNTAX      Counter32
             MAX-ACCESS  read-only
             STATUS      current
             DESCRIPTION
               "The number of IPv6 datagrams successfully
               reassembled.  Note that this counter is incremented
               at the interface to which these datagrams were
               addressed which might not be necessarily the input
               interface for some of the fragments."
             ::= { ipv6PrivIfStatsEntry 17 }

         ipv6PrivIfStatsReasmFails OBJECT-TYPE
             SYNTAX      Counter32
             MAX-ACCESS  read-only
             STATUS      current
             DESCRIPTION
                "The number of failures detected by the IPv6 re-
                assembly algorithm (for whatever reason: timed
                out, errors, etc.).  Note that this is not
                necessarily a count of discarded IPv6 fragments
                since some algorithms (notably the algorithm in
                RFC 815) can lose track of the number of fragments
                by combining them as they are received.
                This counter is incremented at the interface to which
                these fragments were addressed which might not be
                necessarily the input interface for some of the
                fragments."
             ::= { ipv6PrivIfStatsEntry 18 } 
        ipv6PrivIfStatsInMcastPkts OBJECT-TYPE
             SYNTAX      Counter32
             MAX-ACCESS  read-only
             STATUS     current
             DESCRIPTION
                "The number of multicast packets received
                 by the interface"
             ::= { ipv6PrivIfStatsEntry 19 }

         ipv6PrivIfStatsOutMcastPkts OBJECT-TYPE
             SYNTAX      Counter32
             MAX-ACCESS  read-only
             STATUS      current
             DESCRIPTION
                "The number of multicast packets transmitted
                 by the interface"
             ::= { ipv6PrivIfStatsEntry 20 }

 --private item
	 ipv6PrivIfStatsReset OBJECT-TYPE
             SYNTAX      INTEGER (0..2)             
             MAX-ACCESS  read-write
             STATUS      current
             DESCRIPTION
               "Reset the ipv6Priv interface statistics."
             ::= { ipv6PrivIfStatsEntry 21 }       
        

         ipv6PrivIfStatsTcpInitiatedConns OBJECT-TYPE
             SYNTAX     Counter32
             MAX-ACCESS read-only
             STATUS     current
             DESCRIPTION
                ""
             ::= { ipv6PrivIfStatsEntry 22 }

         ipv6PrivIfStatsTcpAcceptedConns OBJECT-TYPE
             SYNTAX      Counter32
             MAX-ACCESS  read-only
             STATUS      current
             DESCRIPTION
               ""
               ::= { ipv6PrivIfStatsEntry 23 }

         ipv6PrivIfStatsTcpEstablishedConns OBJECT-TYPE
             SYNTAX      Counter32
             MAX-ACCESS  read-only
             STATUS      current
             DESCRIPTION
                ""
             ::= { ipv6PrivIfStatsEntry 24 }

         ipv6PrivIfStatsTcpDroppedConns OBJECT-TYPE
             SYNTAX      Counter32
             MAX-ACCESS  read-only
             STATUS      current
             DESCRIPTION
                ""
             ::= { ipv6PrivIfStatsEntry 25 }

         ipv6PrivIfStatsTcpInitiatedDropConns OBJECT-TYPE
             SYNTAX      Counter32
             MAX-ACCESS  read-only
             STATUS      current
             DESCRIPTION
                "The number of locally-addressed datagrams
                received successfully but discarded because of an
                unknown or unsupported protocol. This counter is
                incremented at the interface to which these
                datagrams were addressed which might not be
                necessarily the input interface for some of
                the datagrams."
             ::= { ipv6PrivIfStatsEntry 26 }


         ipv6PrivIfStatsTcpClosedConns OBJECT-TYPE
             SYNTAX      Counter32
             MAX-ACCESS  read-only
             STATUS      current
             DESCRIPTION
                "The number of input datagrams discarded because
                 datagram frame didn't carry enough data."
             ::= { ipv6PrivIfStatsEntry 27 }

         ipv6PrivIfStatsTcpTimeoutDroppedConns OBJECT-TYPE
             SYNTAX      Counter32
             MAX-ACCESS  read-only
             STATUS      current
             DESCRIPTION
                "The number of input IPv6 datagrams for which no
                problems were encountered to prevent their
                continued processing, but which were discarded
                (e.g., for lack of buffer space).  Note that this
                counter does not include any datagrams discarded
                while awaiting re-assembly."
             ::= { ipv6PrivIfStatsEntry 28 }

         ipv6PrivIfStatsTcpRetransTimeout OBJECT-TYPE
             SYNTAX      Counter32
             MAX-ACCESS  read-only
             STATUS      current
             DESCRIPTION
              "The total number of datagrams successfully
              delivered to IPv6 user-protocols (including ICMP).
              This counter is incremented at the interface to
              which these datagrams were addressed which might
              not be necessarily the input interface for some of
              the datagrams."
             ::= { ipv6PrivIfStatsEntry 29 }

         ipv6PrivIfStatsTcpKeepAliveTimeout OBJECT-TYPE
             SYNTAX      Counter32
             MAX-ACCESS  read-only
             STATUS      current
             DESCRIPTION
                "The number of output datagrams which this
                entity received and forwarded to their final
                destinations.  In entities which do not act
                as IPv6 routers, this counter will include
                only those packets which were Source-Routed
                via this entity, and the Source-Route
                processing was successful.  Note that for
                a successfully forwarded datagram the counter
                of the outgoing interface is incremented."
             ::= { ipv6PrivIfStatsEntry 30 }

         ipv6PrivIfStatsTcpKeepAliveProbe OBJECT-TYPE
         	 SYNTAX      Counter32
             MAX-ACCESS  read-only
             STATUS      current
             DESCRIPTION
              "The total number of IPv6 datagrams which local IPv6
              user-protocols (including ICMP) supplied to IPv6 in
              requests for transmission.  Note that this counter
              does not include any datagrams counted in
              ipv6PrivIfStatsOutForwDatagrams."
             ::= { ipv6PrivIfStatsEntry 31 }

         ipv6PrivIfStatsTcpDroppedInKeepalive OBJECT-TYPE
             SYNTAX      Counter32
             MAX-ACCESS  read-only
             STATUS      current
             DESCRIPTION
                 "The number of output IPv6 datagrams for which no
                 problem was encountered to prevent their
                 transmission to their destination, but which were
                 discarded (e.g., for lack of buffer space).  Note
                 that this counter would include datagrams counted
                 in ipv6PrivIfStatsOutForwDatagrams if any such packets
                 met this (discretionary) discard criterion."
             ::= { ipv6PrivIfStatsEntry 32 }

         ipv6PrivIfStatsTcpInPackets OBJECT-TYPE
             SYNTAX      Counter32
             MAX-ACCESS  read-only
             STATUS      current
             DESCRIPTION
                "The number of IPv6 datagrams that have been
                 successfully fragmented at this output interface."
             ::= { ipv6PrivIfStatsEntry 33 }

         ipv6PrivIfStatsTcpInSequence OBJECT-TYPE
             SYNTAX      Counter32
             MAX-ACCESS  read-only
             STATUS      current
             DESCRIPTION
                "The number of IPv6 datagrams that have been
                 discarded because they needed to be fragmented
                 at this output interface but could not be."
             ::= { ipv6PrivIfStatsEntry 34 }

         ipv6PrivIfStatsTcpInBytes OBJECT-TYPE
             SYNTAX      Counter32
             MAX-ACCESS  read-only
             STATUS      current
             DESCRIPTION
                "The number of output datagram fragments that have
                 been generated as a result of fragmentation at
                 this output interface."
             ::= { ipv6PrivIfStatsEntry 35 }

         ipv6PrivIfStatsTcpInChecksumErrs OBJECT-TYPE
             SYNTAX      Counter32
             MAX-ACCESS  read-only
             STATUS      current
             DESCRIPTION
                "The number of IPv6 fragments received which needed
                 to be reassembled at this interface.  Note that this
                 counter is incremented at the interface to which
                 these fragments were addressed which might not
                 be necessarily the input interface for some of
                 the fragments."
             ::= { ipv6PrivIfStatsEntry 36 }

         ipv6PrivIfStatsTcpInOffsetErrs OBJECT-TYPE
             SYNTAX      Counter32
             MAX-ACCESS  read-only
             STATUS      current
             DESCRIPTION
               "The number of IPv6 datagrams successfully
               reassembled.  Note that this counter is incremented
               at the interface to which these datagrams were
               addressed which might not be necessarily the input
               interface for some of the fragments."
             ::= { ipv6PrivIfStatsEntry 37 }

         ipv6PrivIfStatsTcpInShortErrs OBJECT-TYPE
             SYNTAX      Counter32
             MAX-ACCESS  read-only
             STATUS      current
             DESCRIPTION
                "The number of failures detected by the IPv6 re-
                assembly algorithm (for whatever reason: timed
                out, errors, etc.).  Note that this is not
                necessarily a count of discarded IPv6 fragments
                since some algorithms (notably the algorithm in
                RFC 815) can lose track of the number of fragments
                by combining them as they are received.
                This counter is incremented at the interface to which
                these fragments were addressed which might not be
                necessarily the input interface for some of the
                fragments."
             ::= { ipv6PrivIfStatsEntry 38 } 
        ipv6PrivIfStatsTcpInDuplicatePackets OBJECT-TYPE
             SYNTAX      Counter32
             MAX-ACCESS  read-only
             STATUS     current
             DESCRIPTION
                "The number of multicast packets received
                 by the interface"
             ::= { ipv6PrivIfStatsEntry 39 }

         ipv6PrivIfStatsTcpInDuplicateBytes OBJECT-TYPE
             SYNTAX      Counter32
             MAX-ACCESS  read-only
             STATUS      current
             DESCRIPTION
                "The number of multicast packets transmitted
                 by the interface"
             ::= { ipv6PrivIfStatsEntry 40 }

        ipv6PrivIfStatsTcpInPartDuplicatePackets OBJECT-TYPE
             SYNTAX      Counter32
             MAX-ACCESS  read-only
             STATUS      current
             DESCRIPTION
                "The total number of input datagrams received by
                the interface, including those received in error."
             ::= { ipv6PrivIfStatsEntry 41 }

         ipv6PrivIfStatsTcpInPartDuplicateBytes OBJECT-TYPE
             SYNTAX     Counter32
             MAX-ACCESS read-only
             STATUS     current
             DESCRIPTION
                "The number of input datagrams discarded due to
                errors in their IPv6 headers, including version
                number mismatch, other format errors, hop count
                exceeded, errors discovered in processing their
                IPv6 options, etc."
             ::= { ipv6PrivIfStatsEntry 42 }

         ipv6PrivIfStatsTcpInOutOrderPackets OBJECT-TYPE
             SYNTAX      Counter32
             MAX-ACCESS  read-only
             STATUS      current
             DESCRIPTION
               "The number of input datagrams that could not be
               forwarded because their size exceeded the link MTU
               of outgoing interface."
               ::= { ipv6PrivIfStatsEntry 43 }

         ipv6PrivIfStatsTcpInOutOrderBytes OBJECT-TYPE
             SYNTAX      Counter32
             MAX-ACCESS  read-only
             STATUS      current
             DESCRIPTION
                "The number of input datagrams discarded because no
                 route could be found to transmit them to their
                 destination."
             ::= { ipv6PrivIfStatsEntry 44 }

         ipv6PrivIfStatsTcpInAfterWindowPackets OBJECT-TYPE
             SYNTAX      Counter32
             MAX-ACCESS  read-only
             STATUS      current
             DESCRIPTION
                "The number of input datagrams discarded because
                the IPv6 address in their IPv6 header's destination
                field was not a valid address to be received at
                this entity.  This count includes invalid
                addresses (e.g., ::0) and unsupported addresses
                (e.g., addresses with unallocated prefixes).  For
                entities which are not IPv6 routers and therefore
                do not forward datagrams, this counter includes
                datagrams discarded because the destination address
                was not a local address."
             ::= { ipv6PrivIfStatsEntry 45 }

         ipv6PrivIfStatsTcpInAfterWindowBytes OBJECT-TYPE
             SYNTAX      Counter32
             MAX-ACCESS  read-only
             STATUS      current
             DESCRIPTION
                "The number of locally-addressed datagrams
                received successfully but discarded because of an
                unknown or unsupported protocol. This counter is
                incremented at the interface to which these
                datagrams were addressed which might not be
                necessarily the input interface for some of
                the datagrams."
             ::= { ipv6PrivIfStatsEntry 46 }


         ipv6PrivIfStatsTcpInAfterClosePackets OBJECT-TYPE
             SYNTAX      Counter32
             MAX-ACCESS  read-only
             STATUS      current
             DESCRIPTION
                "The number of input datagrams discarded because
                 datagram frame didn't carry enough data."
             ::= { ipv6PrivIfStatsEntry 47 }

         ipv6PrivIfStatsTcpInWindowProbePacks OBJECT-TYPE
             SYNTAX      Counter32
             MAX-ACCESS  read-only
             STATUS      current
             DESCRIPTION
                "The number of input IPv6 datagrams for which no
                problems were encountered to prevent their
                continued processing, but which were discarded
                (e.g., for lack of buffer space).  Note that this
                counter does not include any datagrams discarded
                while awaiting re-assembly."
             ::= { ipv6PrivIfStatsEntry 48 }

         ipv6PrivIfStatsTcpInDuplicateAcks OBJECT-TYPE
             SYNTAX      Counter32
             MAX-ACCESS  read-only
             STATUS      current
             DESCRIPTION
              "The total number of datagrams successfully
              delivered to IPv6 user-protocols (including ICMP).
              This counter is incremented at the interface to
              which these datagrams were addressed which might
              not be necessarily the input interface for some of
              the datagrams."
             ::= { ipv6PrivIfStatsEntry 49 }

         ipv6PrivIfStatsTcpInTooMuchAcks OBJECT-TYPE
             SYNTAX      Counter32
             MAX-ACCESS  read-only
             STATUS      current
             DESCRIPTION
                "The number of output datagrams which this
                entity received and forwarded to their final
                destinations.  In entities which do not act
                as IPv6 routers, this counter will include
                only those packets which were Source-Routed
                via this entity, and the Source-Route
                processing was successful.  Note that for
                a successfully forwarded datagram the counter
                of the outgoing interface is incremented."
             ::= { ipv6PrivIfStatsEntry 50 }

         ipv6PrivIfStatsTcpInAckPackets OBJECT-TYPE
         	 SYNTAX      Counter32
             MAX-ACCESS  read-only
             STATUS      current
             DESCRIPTION
              "The total number of IPv6 datagrams which local IPv6
              user-protocols (including ICMP) supplied to IPv6 in
              requests for transmission.  Note that this counter
              does not include any datagrams counted in
              ipv6PrivIfStatsOutForwDatagrams."
             ::= { ipv6PrivIfStatsEntry 51 }

         ipv6PrivIfStatsTcpInAckBytes OBJECT-TYPE
             SYNTAX      Counter32
             MAX-ACCESS  read-only
             STATUS      current
             DESCRIPTION
                 "The number of output IPv6 datagrams for which no
                 problem was encountered to prevent their
                 transmission to their destination, but which were
                 discarded (e.g., for lack of buffer space).  Note
                 that this counter would include datagrams counted
                 in ipv6PrivIfStatsOutForwDatagrams if any such packets
                 met this (discretionary) discard criterion."
             ::= { ipv6PrivIfStatsEntry 52 }

         ipv6PrivIfStatsTcpInWindowUpdate OBJECT-TYPE
             SYNTAX      Counter32
             MAX-ACCESS  read-only
             STATUS      current
             DESCRIPTION
                "The number of IPv6 datagrams that have been
                 successfully fragmented at this output interface."
             ::= { ipv6PrivIfStatsEntry 53 }

         ipv6PrivIfStatsTcpOutDelayedAcks OBJECT-TYPE
             SYNTAX      Counter32
             MAX-ACCESS  read-only
             STATUS      current
             DESCRIPTION
                "The number of IPv6 datagrams that have been
                 discarded because they needed to be fragmented
                 at this output interface but could not be."
             ::= { ipv6PrivIfStatsEntry 54 }

         ipv6PrivIfStatsTcpOutPackets OBJECT-TYPE
             SYNTAX      Counter32
             MAX-ACCESS  read-only
             STATUS      current
             DESCRIPTION
                "The number of output datagram fragments that have
                 been generated as a result of fragmentation at
                 this output interface."
             ::= { ipv6PrivIfStatsEntry 55 }

         ipv6PrivIfStatsTcpOutDataPackets OBJECT-TYPE
             SYNTAX      Counter32
             MAX-ACCESS  read-only
             STATUS      current
             DESCRIPTION
                "The number of IPv6 fragments received which needed
                 to be reassembled at this interface.  Note that this
                 counter is incremented at the interface to which
                 these fragments were addressed which might not
                 be necessarily the input interface for some of
                 the fragments."
             ::= { ipv6PrivIfStatsEntry 56 }

         ipv6PrivIfStatsTcpOutDataBytes OBJECT-TYPE
             SYNTAX      Counter32
             MAX-ACCESS  read-only
             STATUS      current
             DESCRIPTION
               "The number of IPv6 datagrams successfully
               reassembled.  Note that this counter is incremented
               at the interface to which these datagrams were
               addressed which might not be necessarily the input
               interface for some of the fragments."
             ::= { ipv6PrivIfStatsEntry 57 }

         ipv6PrivIfStatsTcpOutRetransmitPackets OBJECT-TYPE
             SYNTAX      Counter32
             MAX-ACCESS  read-only
             STATUS      current
             DESCRIPTION
                "The number of failures detected by the IPv6 re-
                assembly algorithm (for whatever reason: timed
                out, errors, etc.).  Note that this is not
                necessarily a count of discarded IPv6 fragments
                since some algorithms (notably the algorithm in
                RFC 815) can lose track of the number of fragments
                by combining them as they are received.
                This counter is incremented at the interface to which
                these fragments were addressed which might not be
                necessarily the input interface for some of the
                fragments."
             ::= { ipv6PrivIfStatsEntry 58 } 
             
        ipv6PrivIfStatsTcpOutRetransmitBytes OBJECT-TYPE
             SYNTAX      Counter32
             MAX-ACCESS  read-only
             STATUS     current
             DESCRIPTION
                "The number of multicast packets received
                 by the interface"
             ::= { ipv6PrivIfStatsEntry 59 }

         ipv6PrivIfStatsTcpOutAcks OBJECT-TYPE
             SYNTAX      Counter32
             MAX-ACCESS  read-only
             STATUS      current
             DESCRIPTION
                "The number of multicast packets transmitted
                 by the interface"
             ::= { ipv6PrivIfStatsEntry 60 }

	ipv6PrivIfStatsTcpOutWindowProbes OBJECT-TYPE
             SYNTAX      Counter32
             MAX-ACCESS  read-only
             STATUS      current
             DESCRIPTION
                "The total number of input datagrams received by
                the interface, including those received in error."
             ::= { ipv6PrivIfStatsEntry 61 }

         ipv6PrivIfStatsTcpOutUrgentPackets OBJECT-TYPE
             SYNTAX     Counter32
             MAX-ACCESS read-only
             STATUS     current
             DESCRIPTION
                "The number of input datagrams discarded due to
                errors in their IPv6 headers, including version
                number mismatch, other format errors, hop count
                exceeded, errors discovered in processing their
                IPv6 options, etc."
             ::= { ipv6PrivIfStatsEntry 62 }

         ipv6PrivIfStatsTcpOutWindowUpdates OBJECT-TYPE
             SYNTAX      Counter32
             MAX-ACCESS  read-only
             STATUS      current
             DESCRIPTION
               "The number of input datagrams that could not be
               forwarded because their size exceeded the link MTU
               of outgoing interface."
               ::= { ipv6PrivIfStatsEntry 63 }

         ipv6PrivIfStatsTcpOutControls OBJECT-TYPE
             SYNTAX      Counter32
             MAX-ACCESS  read-only
             STATUS      current
             DESCRIPTION
                "The number of input datagrams discarded because no
                 route could be found to transmit them to their
                 destination."
             ::= { ipv6PrivIfStatsEntry 64 }

         ipv6PrivIfStatsTcpReset OBJECT-TYPE
             SYNTAX      INTEGER (0..2)             
             MAX-ACCESS  read-write
             STATUS      current
             DESCRIPTION
               "Reset the ipv6Priv interface statistics."
             ::= { ipv6PrivIfStatsEntry 65 }

         ipv6PrivIfStatsUdpInPackets OBJECT-TYPE
             SYNTAX      Counter32
             MAX-ACCESS  read-only
             STATUS      current
             DESCRIPTION
                "The number of locally-addressed datagrams
                received successfully but discarded because of an
                unknown or unsupported protocol. This counter is
                incremented at the interface to which these
                datagrams were addressed which might not be
                necessarily the input interface for some of
                the datagrams."
             ::= { ipv6PrivIfStatsEntry 66 }


         ipv6PrivIfStatsUdpInShorerThanHeaders OBJECT-TYPE
             SYNTAX      Counter32
             MAX-ACCESS  read-only
             STATUS      current
             DESCRIPTION
                "The number of input datagrams discarded because
                 datagram frame didn't carry enough data."
             ::= { ipv6PrivIfStatsEntry 67 }

         ipv6PrivIfStatsUdpInCheckError OBJECT-TYPE
             SYNTAX      Counter32
             MAX-ACCESS  read-only
             STATUS      current
             DESCRIPTION
                "The number of input IPv6 datagrams for which no
                problems were encountered to prevent their
                continued processing, but which were discarded
                (e.g., for lack of buffer space).  Note that this
                counter does not include any datagrams discarded
                while awaiting re-assembly."
             ::= { ipv6PrivIfStatsEntry 68 }

         ipv6PrivIfStatsUdpInInvalidLength OBJECT-TYPE
             SYNTAX      Counter32
             MAX-ACCESS  read-only
             STATUS      current
             DESCRIPTION
              "The total number of datagrams successfully
              delivered to IPv6 user-protocols (including ICMP).
              This counter is incremented at the interface to
              which these datagrams were addressed which might
              not be necessarily the input interface for some of
              the datagrams."
             ::= { ipv6PrivIfStatsEntry 69 }

         ipv6PrivIfStatsUdpInNoSocketOnPort OBJECT-TYPE
             SYNTAX      Counter32
             MAX-ACCESS  read-only
             STATUS      current
             DESCRIPTION
                "The number of output datagrams which this
                entity received and forwarded to their final
                destinations.  In entities which do not act
                as IPv6 routers, this counter will include
                only those packets which were Source-Routed
                via this entity, and the Source-Route
                processing was successful.  Note that for
                a successfully forwarded datagram the counter
                of the outgoing interface is incremented."
             ::= { ipv6PrivIfStatsEntry 70 }         

         ipv6PrivIfStatsUdpInNoMulticastPort OBJECT-TYPE
             SYNTAX      Counter32
             MAX-ACCESS  read-only
             STATUS      current
             DESCRIPTION
                 "The number of output IPv6 datagrams for which no
                 problem was encountered to prevent their
                 transmission to their destination, but which were
                 discarded (e.g., for lack of buffer space).  Note
                 that this counter would include datagrams counted
                 in ipv6PrivIfStatsOutForwDatagrams if any such packets
                 met this (discretionary) discard criterion."
             ::= { ipv6PrivIfStatsEntry 71 }

         ipv6PrivIfStatsUdpInSocketFull OBJECT-TYPE
             SYNTAX      Counter32
             MAX-ACCESS  read-only
             STATUS      current
             DESCRIPTION
                "The number of IPv6 datagrams that have been
                 successfully fragmented at this output interface."
             ::= { ipv6PrivIfStatsEntry 72 }

         ipv6PrivIfStatsUdpInPcbCacheMiss OBJECT-TYPE
             SYNTAX      Counter32
             MAX-ACCESS  read-only
             STATUS      current
             DESCRIPTION
                "The number of IPv6 datagrams that have been
                 discarded because they needed to be fragmented
                 at this output interface but could not be."
             ::= { ipv6PrivIfStatsEntry 73 }

         ipv6PrivIfStatsUdpOutPackets OBJECT-TYPE
             SYNTAX      Counter32
             MAX-ACCESS  read-only
             STATUS      current
             DESCRIPTION
                "The number of output datagram fragments that have
                 been generated as a result of fragmentation at
                 this output interface."
             ::= { ipv6PrivIfStatsEntry 74 }

         ipv6PrivIfStatsUdpReset OBJECT-TYPE
             SYNTAX      INTEGER (0..2)             
             MAX-ACCESS  read-write
             STATUS      current
             DESCRIPTION
               "Reset the ipv6Priv interface statistics."
             ::= { ipv6PrivIfStatsEntry 75 }             

         -- Address Prefix table

         -- The IPv6 Address Prefix table contains information on
         -- the entity's IPv6 Address Prefixes that are associated
         -- with IPv6 interfaces.

         ipv6PrivAddrPrefixTable OBJECT-TYPE
             SYNTAX  SEQUENCE OF Ipv6PrivAddrPrefixEntry
             MAX-ACCESS  not-accessible
             STATUS      current
             DESCRIPTION
                 "The list of IPv6 address prefixes of
                 IPv6 interfaces."
             ::= { ipv6PrivMIBObjects 7 }

         ipv6PrivAddrPrefixEntry OBJECT-TYPE
             SYNTAX  Ipv6PrivAddrPrefixEntry
             MAX-ACCESS  not-accessible
             STATUS      current
             DESCRIPTION
                 "An interface entry containing objects of
                 a particular IPv6 address prefix."
             INDEX   { ipv6PrivIfIndex,
                       ipv6PrivAddrPrefix,
                       ipv6PrivAddrPrefixLength }
             ::= { ipv6PrivAddrPrefixTable 1 }

         Ipv6PrivAddrPrefixEntry ::= SEQUENCE {
         	  ipv6PrivAddrPrefix                     Ipv6AddressPrefix,
              ipv6PrivAddrPrefixLength               INTEGER,
              ipv6PrivAddrPrefixOnLinkFlag           TruthValue,
              ipv6PrivAddrPrefixAutonomousFlag       TruthValue,
              ipv6PrivAddrPrefixAdvPreferredLifetime Unsigned32,
              ipv6PrivAddrPrefixAdvValidLifetime     Unsigned32
             }

         ipv6PrivAddrPrefix OBJECT-TYPE
             SYNTAX      Ipv6AddressPrefix
             MAX-ACCESS  read-only
             STATUS      current
             DESCRIPTION
               "The prefix associated with the this interface."
             ::= { ipv6PrivAddrPrefixEntry 1 }

         ipv6PrivAddrPrefixLength OBJECT-TYPE
             SYNTAX      INTEGER (0..128)
             UNITS       "bits"
             MAX-ACCESS  read-only
             STATUS      current
             DESCRIPTION
               "The length of the prefix (in bits)."
             ::= { ipv6PrivAddrPrefixEntry 2 }

         ipv6PrivAddrPrefixOnLinkFlag OBJECT-TYPE
             SYNTAX      TruthValue
             MAX-ACCESS  read-only
             STATUS      current
             DESCRIPTION
               "This object has the value 'true(1)', if this
               prefix can be used  for on-link determination
               and the value 'false(2)' otherwise."
             ::= { ipv6PrivAddrPrefixEntry 3 }

         ipv6PrivAddrPrefixAutonomousFlag OBJECT-TYPE
             SYNTAX      TruthValue
             MAX-ACCESS  read-only
             STATUS      current
             DESCRIPTION
               "Autonomous address configuration flag. When
               true(1), indicates that this prefix can be used
               for autonomous address configuration (i.e. can
               be used to form a local interface address).
               If false(2), it is not used to autoconfigure
               a local interface address."
             ::= { ipv6PrivAddrPrefixEntry 4 }
             
           ipv6PrivAddrPrefixAdvPreferredLifetime OBJECT-TYPE
             SYNTAX      Unsigned32
             UNITS       "seconds"
             MAX-ACCESS  read-only
             STATUS      current
             DESCRIPTION
                "It is the length of time in seconds that this
                prefix will remain preferred, i.e. time until
                deprecation.  A value of 4,294,967,295 represents
                infinity.

                The address generated from a deprecated prefix
                should no longer be used as a source address in
                new communications, but packets received on such
                an interface are processed as expected."
             ::= { ipv6PrivAddrPrefixEntry 5 }

         ipv6PrivAddrPrefixAdvValidLifetime OBJECT-TYPE
             SYNTAX      Unsigned32
             UNITS       "seconds"
             MAX-ACCESS  read-only
             STATUS      current
             DESCRIPTION
               "It is the length of time in seconds that this
               prefix will remain valid, i.e. time until
               invalidation.  A value of 4,294,967,295 represents
               infinity.

               The address generated from an invalidated prefix
               should not appear as the destination or source
               address of a packet."
             ::= { ipv6PrivAddrPrefixEntry 6 }


         -- the IPv6 Address table

         -- The IPv6 address table contains this node's IPv6
         -- addressing information.

         ipv6PrivAddrTable OBJECT-TYPE
            SYNTAX      SEQUENCE OF Ipv6AddrEntry
            MAX-ACCESS  not-accessible
            STATUS      current
            DESCRIPTION
              "The table of addressing information relevant to
              this node's interface addresses."
            ::= { ipv6PrivMIBObjects 8 }
         ipv6PrivAddrEntry OBJECT-TYPE
            SYNTAX      Ipv6AddrEntry
            MAX-ACCESS  not-accessible
            STATUS      current
            DESCRIPTION
                "The addressing information for one of this
                node's interface addresses."
            INDEX   { ipv6PrivIfIndex, ipv6PrivAddrAddress }
            ::= { ipv6PrivAddrTable 1 }

         Ipv6AddrEntry ::=
            SEQUENCE {
                 ipv6PrivAddrAddress        Ipv6Address,
                 ipv6PrivAddrPfxLength      INTEGER,
                 ipv6PrivAddrType           INTEGER,
                 ipv6PrivAddrAnycastFlag    TruthValue,
                 ipv6PrivAddrStatus         INTEGER
                }

         ipv6PrivAddrAddress OBJECT-TYPE
            SYNTAX      Ipv6Address
            MAX-ACCESS  read-only
            STATUS      current
            DESCRIPTION
              "The IPv6 address to which this entry's addressing
              information pertains."
            ::= { ipv6PrivAddrEntry 1 }

         ipv6PrivAddrPfxLength OBJECT-TYPE
            SYNTAX      INTEGER(0..128)
            UNITS       "bits"
            MAX-ACCESS  read-only
            STATUS      current
            DESCRIPTION
              "The length of the prefix (in bits) associated with
              the IPv6 address of this entry."
            ::= { ipv6PrivAddrEntry 2 }

         ipv6PrivAddrType OBJECT-TYPE
            SYNTAX      INTEGER {
                                -- address has been formed
                                -- using stateless
                 stateless(1),  -- autoconfiguration

                                -- address has been acquired
                                -- by stateful means
                                -- (e.g. DHCPv6, manual
                 stateful(2),   -- configuration)
                 
                                -- type can not be determined
                 unknown(3)     -- for some reason.
               }
            MAX-ACCESS  read-only
            STATUS      current
            DESCRIPTION
               "The type of address. Note that 'stateless(1)'
               refers to an address that was statelessly
               autoconfigured; 'stateful(2)' refers to a address
               which was acquired by via a stateful protocol
               (e.g. DHCPv6, manual configuration)."
            ::= { ipv6PrivAddrEntry 3 }

         ipv6PrivAddrAnycastFlag OBJECT-TYPE
             SYNTAX      TruthValue
             MAX-ACCESS  read-only
             STATUS      current
             DESCRIPTION
               "This object has the value 'true(1)', if this
               address is an anycast address and the value
               'false(2)' otherwise."
             ::= { ipv6PrivAddrEntry 4 }

         ipv6PrivAddrStatus OBJECT-TYPE
            SYNTAX      INTEGER {
                     preferred(1),

                     deprecated(2),

                     invalid(3),

                     inaccessible(4),

                     unknown(5)   -- status can not be determined
                                  -- for some reason.
                    }
            MAX-ACCESS  read-only
            STATUS      current
            DESCRIPTION
              "Address status.  The preferred(1) state indicates
              that this is a valid address that can appear as
              the destination or source address of a packet.
              The deprecated(2) state indicates that this is
              a valid but deprecated address that should no longer
              be used as a source address in new communications,
              but packets addressed to such an address are
              processed as expected. The invalid(3) state indicates
              that this is not valid address which should not 
              appear as the destination or source address of
              a packet. The inaccessible(4) state indicates that
              the address is not accessible because the interface
              to which this address is assigned is not operational."
            ::= { ipv6PrivAddrEntry 5 }


         -- IPv6 Routing objects

         ipv6PrivRouteNumber OBJECT-TYPE
             SYNTAX      Gauge32
             MAX-ACCESS  read-only
             STATUS      current
             DESCRIPTION
               "The number of current ipv6PrivRouteTable entries.
               This is primarily to avoid having to read
               the table in order to determine this number."
             ::= { ipv6PrivMIBObjects 9 }

         ipv6PrivDiscardedRoutes OBJECT-TYPE
             SYNTAX      Counter32
             MAX-ACCESS  read-only
             STATUS      current
             DESCRIPTION
               "The number of routing entries which were chosen
                to be discarded even though they are valid.  One
                possible reason for discarding such an entry could
                be to free-up buffer space for other routing
                entries."
             ::= { ipv6PrivMIBObjects 10 }


         -- IPv6 Routing table

         ipv6PrivRouteTable OBJECT-TYPE
             SYNTAX     SEQUENCE OF Ipv6PrivRouteEntry
             MAX-ACCESS not-accessible
             STATUS     current
             DESCRIPTION
               "IPv6 Routing table. This table contains
               an entry for each valid IPv6 unicast route
               that can be used for packet forwarding
               determination."
             ::= { ipv6PrivMIBObjects 11 }

         ipv6PrivRouteEntry OBJECT-TYPE
             SYNTAX     Ipv6PrivRouteEntry
             MAX-ACCESS not-accessible
             STATUS     current
             DESCRIPTION
                     "A routing entry."   
             INDEX   {  
             		   ipv6PrivRouteVrid,		
             		   ipv6PrivRouteDest,
                       ipv6PrivRoutePfxLength,
                       ipv6PrivRouteIndex,
					   ipv6PrivRouteIndexNextHop}
             ::= { ipv6PrivRouteTable 1 }

         Ipv6PrivRouteEntry ::= SEQUENCE {   
         		 ipv6PrivRouteVrid	         INTEGER,
                 ipv6PrivRouteDest           Ipv6Address,
                 ipv6PrivRoutePfxLength      INTEGER,
                 ipv6PrivRouteIndex          Unsigned32,
				 ipv6PrivRouteIndexNextHop	 Ipv6Address,
                 ipv6PrivRouteIfIndex        Ipv6IfIndexOrZero,
                 ipv6PrivRouteNextHop        Ipv6Address,
                 ipv6PrivRouteType           INTEGER,
                 ipv6PrivRouteProtocol       INTEGER,
                 ipv6PrivRoutePolicy         Integer32,
                 ipv6PrivRouteAge            Unsigned32,
                 ipv6PrivRouteNextHopRDI     Unsigned32,
                 ipv6PrivRouteMetric         Unsigned32,
                 ipv6PrivRouteWeight         Unsigned32,
                 ipv6PrivRouteInfo           RowPointer,
                 ipv6PrivRouteValid          TruthValue
             }
         ipv6PrivRouteVrid   OBJECT-TYPE
             SYNTAX     INTEGER
             MAX-ACCESS read-only
             STATUS     current
             DESCRIPTION
               "the vpn instance id."
             ::= { ipv6PrivRouteEntry 1 }

         
         ipv6PrivRouteDest OBJECT-TYPE
             SYNTAX     Ipv6Address
             MAX-ACCESS read-only
             STATUS     current
             DESCRIPTION
               "The destination IPv6 address of this route.
               This object may not take a Multicast address
               value."
             ::= { ipv6PrivRouteEntry 2 }

         ipv6PrivRoutePfxLength OBJECT-TYPE
             SYNTAX     INTEGER(0..128)
             UNITS      "bits"
             MAX-ACCESS read-only
             STATUS     current
             DESCRIPTION
               "Indicates the prefix length of the destination
               address."
             ::= { ipv6PrivRouteEntry 3 }

         ipv6PrivRouteIndex OBJECT-TYPE
             SYNTAX     Unsigned32
             MAX-ACCESS read-only 
             STATUS     current
             DESCRIPTION
               "The value which uniquely identifies the route
               among the routes to the same network layer
               destination.  The way this value is chosen is
               implementation specific but it must be unique for
               ipv6PrivRouteDest/ipv6PrivRoutePfxLength pair and remain
               constant for the life of the route."
             ::= { ipv6PrivRouteEntry 4 }
		
		 ipv6PrivRouteIndexNextHop OBJECT-TYPE
             SYNTAX     Ipv6Address
             MAX-ACCESS read-only
             STATUS     current
             DESCRIPTION
               "The next IPv6 address of this route."
             ::= { ipv6PrivRouteEntry 5 }
			 
         ipv6PrivRouteIfIndex OBJECT-TYPE
             SYNTAX     Ipv6IfIndexOrZero
             MAX-ACCESS read-write
             STATUS     current
             DESCRIPTION
               "The index value which uniquely identifies the local
               interface through which the next hop of this
               route should be reached.  The interface identified
               by a particular value of this index is the same
               interface as identified by the same value of
               ipv6PrivIfIndex.  For routes of the discard type this
               value can be zero."
             ::= { ipv6PrivRouteEntry 6 }

         ipv6PrivRouteNextHop OBJECT-TYPE
             SYNTAX     Ipv6Address
             MAX-ACCESS read-write
             STATUS     current
             DESCRIPTION
               "On remote routes, the address of the next
               system en route;  otherwise, ::0
               ('00000000000000000000000000000000'H in ASN.1
               string representation)."
             ::= { ipv6PrivRouteEntry 7 }

         ipv6PrivRouteType OBJECT-TYPE
             SYNTAX     INTEGER {
                other(1),     -- none of the following

                              -- an route indicating that
                              -- packets to destinations
                              -- matching this route are
                discard(2),   -- to be discarded

                              -- route to directly
                local(3),     -- connected (sub-)network

                              -- route to a remote
                remote(4)     -- destination

             }
             MAX-ACCESS read-only
             STATUS     current
             DESCRIPTION
                "The type of route. Note that 'local(3)' refers
                to a route for which the next hop is the final
                destination; 'remote(4)' refers to a route for
                which  the  next  hop is not the final
                destination; 'discard(2)' refers to a route
                indicating that packets to destinations matching
                this route are to be discarded (sometimes called
                black-hole route)."
             ::= { ipv6PrivRouteEntry 8}

         ipv6PrivRouteProtocol OBJECT-TYPE
             SYNTAX     INTEGER {
               other(1),   -- none of the following

                           -- non-protocol information,
                           -- e.g., manually configured
               local(2),   -- entries

               netmgmt(3), -- static route

                           -- obtained via Neighbor
                           -- Discovery protocol,
               ndisc(4),   -- e.g., result of Redirect

                           -- the following are all
                           -- dynamic routing protocols
               rip(5),     -- RIPng
               ospf(6),    -- Open Shortest Path First
               bgp(7),     -- Border Gateway Protocol
               idrp(8),    -- InterDomain Routing Protocol
               igrp(9)     -- InterGateway Routing Protocol
             }
             MAX-ACCESS read-only
             STATUS     current
             DESCRIPTION
               "The routing mechanism via which this route was
               learned."
             ::= { ipv6PrivRouteEntry 9 }

         ipv6PrivRoutePolicy OBJECT-TYPE
             SYNTAX     Integer32
             MAX-ACCESS read-only
             STATUS     current
             DESCRIPTION
              "The general set of conditions that would cause the
              selection of one multipath route (set of next hops
              for a given destination) is referred to as 'policy'.
              Unless the mechanism indicated by ipv6PrivRouteProtocol
              specified otherwise, the policy specifier is the
              8-bit Traffic Class field of the IPv6 packet header
              that is zero extended at the left to a 32-bit value.

              Protocols defining 'policy' otherwise must either
              define a set of values which are valid for
              this object or must implement an integer-
              instanced  policy table for which this object's
              value acts as an index."
             ::= { ipv6PrivRouteEntry 10}

         ipv6PrivRouteAge OBJECT-TYPE
             SYNTAX     Unsigned32
             UNITS      "seconds"
             MAX-ACCESS read-only
             STATUS     current
             DESCRIPTION
                "The number of seconds since this route was last
                updated or otherwise determined to be correct.
                Note that no semantics of `too old' can be implied
                except through knowledge of the routing protocol
                by which the route was learned."
             ::= { ipv6PrivRouteEntry 11 }

         ipv6PrivRouteNextHopRDI OBJECT-TYPE
             SYNTAX     Unsigned32
             MAX-ACCESS read-only
             STATUS     current
             DESCRIPTION
                "The Routing Domain ID of the Next Hop.
                The  semantics of this object are determined by
                the routing-protocol specified in  the  route's
                ipv6PrivRouteProtocol value.   When  this object is
                unknown or not relevant its value should be set
                to zero."
             ::= { ipv6PrivRouteEntry 12 }

         ipv6PrivRouteMetric OBJECT-TYPE
             SYNTAX     Unsigned32
             MAX-ACCESS read-write
             STATUS     current
             DESCRIPTION             
                "The routing metric for this route. The
                semantics of this metric are determined by the
                routing protocol specified in the route's
                ipv6PrivRouteProtocol value.  When this is unknown
                or not relevant to the protocol indicated by
                ipv6PrivRouteProtocol, the object value should be
                set to its maximum value (4,294,967,295)."
             ::= { ipv6PrivRouteEntry 13 }

         ipv6PrivRouteWeight OBJECT-TYPE
             SYNTAX     Unsigned32
             MAX-ACCESS read-only
             STATUS     current
             DESCRIPTION
                "The system internal weight value for this route.
                The semantics of this value are determined by
                the implementation specific rules. Generally,
                within routes with the same ipv6PrivRoutePolicy value,
                the lower the weight value the more preferred is
                the route."
             ::= { ipv6PrivRouteEntry 14 }

         ipv6PrivRouteInfo OBJECT-TYPE
             SYNTAX     RowPointer
             MAX-ACCESS read-only
             STATUS     current
             DESCRIPTION
                "A reference to MIB definitions specific to the
                particular routing protocol which is responsible
                for this route, as determined by the  value
                specified  in the route's ipv6PrivRouteProto value.
                If this information is not present,  its  value
                should be set to the OBJECT ID { 0 0 },
                which is a syntactically valid object  identifier,
                and any implementation conforming to ASN.1
                and the Basic Encoding Rules must  be  able  to
                generate and recognize this value."
             ::= { ipv6PrivRouteEntry 15 }

         ipv6PrivRouteValid OBJECT-TYPE
             SYNTAX     TruthValue
             MAX-ACCESS read-write
             STATUS     current
             DESCRIPTION
                "Setting this object to the value 'false(2)' has
                the effect of invalidating the corresponding entry
                in the ipv6PrivRouteTable object.  That is, it
                effectively disassociates the destination
                identified with said entry from the route
                identified with said entry.  It is an
                implementation-specific matter as to whether the
                agent removes an invalidated entry from the table.
                Accordingly, management stations must be prepared
                to receive tabular information from agents that
                corresponds to entries not currently in use.
                Proper interpretation of such entries requires
                examination of the relevant ipv6PrivRouteValid
                object."
             DEFVAL  { true }
             ::= { ipv6PrivRouteEntry 16 }


         -- IPv6 Address Translation table

         ipv6PrivNetToMediaTable OBJECT-TYPE
             SYNTAX      SEQUENCE OF Ipv6PrivNetToMediaEntry
             MAX-ACCESS  not-accessible
             STATUS      current
             DESCRIPTION
               "The IPv6 Address Translation table used for
               mapping from IPv6 addresses to physical addresses.

               The IPv6 address translation table contain the
               Ipv6Address to `physical' address equivalencies.
               Some interfaces do not use translation tables
               for determining address equivalencies; if all
               interfaces are of this type, then the Address
               Translation table is empty, i.e., has zero
               entries."
             ::= { ipv6PrivMIBObjects 12 }

         ipv6PrivNetToMediaEntry OBJECT-TYPE
             SYNTAX     Ipv6PrivNetToMediaEntry
             MAX-ACCESS not-accessible
             STATUS     current
             DESCRIPTION
               "Each entry contains one IPv6 address to `physical'
               address equivalence."
             INDEX   { ipv6PrivIfIndex,
                       ipv6PrivNetToMediaNetAddress }
             ::= { ipv6PrivNetToMediaTable 1 }

         Ipv6PrivNetToMediaEntry ::= SEQUENCE {
                 ipv6PrivNetToMediaNetAddress
                     Ipv6Address,
                 ipv6PrivNetToMediaPhysAddress
                     PhysAddress,
                 ipv6PrivNetToMediaType
                     INTEGER,
                 ipv6PrivIfNetToMediaState
                     INTEGER,
                 ipv6PrivIfNetToMediaLastUpdated
                     TimeStamp,
                 ipv6PrivNetToMediaValid
                     TruthValue,
                 ipv6PrivNetToMediaPhyPort
                 	 INTEGER,
                 ipv6PrivNetToMediaAgingTime
                 	 INTEGER	 
             }

         ipv6PrivNetToMediaNetAddress OBJECT-TYPE
             SYNTAX     Ipv6Address
             MAX-ACCESS read-only
             STATUS     current
             DESCRIPTION
                "The IPv6 Address corresponding to
                the media-dependent `physical' address."
             ::= { ipv6PrivNetToMediaEntry 1 }

         ipv6PrivNetToMediaPhysAddress OBJECT-TYPE
             SYNTAX     PhysAddress
             MAX-ACCESS read-write
             STATUS     current
             DESCRIPTION
               "The media-dependent `physical' address."
             ::= { ipv6PrivNetToMediaEntry 2 }

         ipv6PrivNetToMediaType OBJECT-TYPE
             SYNTAX     INTEGER {
                         other(1),    -- none of the following
                         dynamic(2),  -- dynamically resolved
                         static(3),   -- statically configured
                         local(4)     -- local interface
                        }
             MAX-ACCESS read-only
             STATUS     current
             DESCRIPTION
                     "The type of the mapping. The 'dynamic(2)' type
                     indicates that the IPv6 address to physical
                     addresses mapping has been dynamically
                     resolved using the IPv6 Neighbor Discovery
                     protocol. The static(3)' types indicates that
                     the mapping has been statically configured.
                     The local(4) indicates that the mapping is
                     provided for an entity's own interface address."
             ::= { ipv6PrivNetToMediaEntry 3 }
             
         ipv6PrivIfNetToMediaState OBJECT-TYPE
            SYNTAX      INTEGER {
                     reachable(1), -- confirmed reachability

                     stale(2),     -- unconfirmed reachability

                     delay(3),     -- waiting for reachability
                                   -- confirmation before entering
                                   -- the probe state

                     probe(4),     -- actively probing

                     invalid(5),   -- an invalidated mapping

                     unknown(6)    -- state can not be determined
                                   -- for some reason.
                    }
            MAX-ACCESS  read-only
            STATUS      current
            DESCRIPTION
                "The Neighbor Unreachability Detection [8] state
                for the interface when the address mapping in
                this entry is used."
            ::= { ipv6PrivNetToMediaEntry 4 }

        ipv6PrivIfNetToMediaLastUpdated OBJECT-TYPE
            SYNTAX      TimeStamp
            MAX-ACCESS  read-only
            STATUS      current
            DESCRIPTION
                "The value of sysUpTime at the time this entry
                was last updated.  If this entry was updated prior
                to the last re-initialization of the local network
                management subsystem, then this object contains
                a zero value."
            ::= { ipv6PrivNetToMediaEntry 5 }

         ipv6PrivNetToMediaValid OBJECT-TYPE
             SYNTAX     TruthValue
             MAX-ACCESS read-write
             STATUS     current
             DESCRIPTION
              "Setting this object to the value 'false(2)' has
              the effect of invalidating the corresponding entry
              in the ipv6PrivNetToMediaTable.  That is, it effectively
              disassociates the interface identified with said
              entry from the mapping identified with said entry.
              It is an implementation-specific matter as to
              whether the agent removes an invalidated entry
              from the table.  Accordingly, management stations
              must be prepared to receive tabular information
              from agents that corresponds to entries not
              currently in use.  Proper interpretation of such
              entries requires examination of the relevant
              ipv6PrivNetToMediaValid object."
             DEFVAL  { true }
             ::= { ipv6PrivNetToMediaEntry 6 }
             
          ipv6PrivNetToMediaPhyPort OBJECT-TYPE
             SYNTAX     INTEGER
             MAX-ACCESS read-write
             STATUS     current
             DESCRIPTION
              "The Phy Port of ipv6 address."
             ::= { ipv6PrivNetToMediaEntry 7 }    
             
         ipv6PrivNetToMediaAgingTime OBJECT-TYPE
             SYNTAX     INTEGER
             MAX-ACCESS read-only
             STATUS     current
             DESCRIPTION
              "The ipv6 neighbor aging time."
             ::= { ipv6PrivNetToMediaEntry 8 }   
                  
ipv6PrivTcpConnTable OBJECT-TYPE
   SYNTAX      SEQUENCE OF Ipv6PrivTcpConnEntry
   MAX-ACCESS  not-accessible
   STATUS      current
   DESCRIPTION
        "A table containing TCP connection-specific information,
         for only those connections whose endpoints are IPv6 addresses."
   ::= { ipv6PrivMIBObjects 13 }

ipv6PrivTcpConnEntry OBJECT-TYPE
   SYNTAX      Ipv6PrivTcpConnEntry
   MAX-ACCESS  not-accessible
   STATUS      current
   DESCRIPTION
        "A conceptual row of the ipv6PrivTcpConnTable containing
         information about a particular current TCP connection.
         Each row of this table is transient, in that it ceases to
         exist when (or soon after) the connection makes the transition
         to the CLOSED state.

         Note that conceptual rows in this table require an additional
         index object compared to tcpConnTable, since IPv6 addresses
         are not guaranteed to be unique on the managed node."
   INDEX   { ipv6PrivTcpConnLocalAddress,
             ipv6PrivTcpConnLocalPort,
             ipv6PrivTcpConnRemAddress,
             ipv6PrivTcpConnRemPort,
             ipv6PrivTcpConnIfIndex }
   ::= { ipv6PrivTcpConnTable 1 }

Ipv6PrivTcpConnEntry ::=
   SEQUENCE { ipv6PrivTcpConnLocalAddress    Ipv6Address,
              ipv6PrivTcpConnLocalPort       INTEGER,
              ipv6PrivTcpConnRemAddress      Ipv6Address,
              ipv6PrivTcpConnRemPort         INTEGER,
              ipv6PrivTcpConnIfIndex         Ipv6IfIndexOrZero,
              ipv6PrivTcpConnState           INTEGER }

ipv6PrivTcpConnLocalAddress OBJECT-TYPE
   SYNTAX     Ipv6Address
   MAX-ACCESS read-only
   STATUS     current
   DESCRIPTION
        "The local IPv6 address for this TCP connection. In
         the case of a connection in the listen state which
         is willing to accept connections for any IPv6
         address associated with the managed node, the value
         ::0 is used."
   ::= { ipv6PrivTcpConnEntry 1 }

ipv6PrivTcpConnLocalPort OBJECT-TYPE
   SYNTAX     INTEGER (0..65535)
   MAX-ACCESS read-only
   STATUS     current
   DESCRIPTION
        "The local port number for this TCP connection."
   ::= { ipv6PrivTcpConnEntry 2 }

ipv6PrivTcpConnRemAddress OBJECT-TYPE
   SYNTAX     Ipv6Address
   MAX-ACCESS read-only
   STATUS     current
   DESCRIPTION
        "The remote IPv6 address for this TCP connection."
   ::= { ipv6PrivTcpConnEntry 3 }

ipv6PrivTcpConnRemPort OBJECT-TYPE
   SYNTAX     INTEGER (0..65535)
   MAX-ACCESS read-only
   STATUS     current
   DESCRIPTION
        "The remote port number for this TCP connection."
   ::= { ipv6PrivTcpConnEntry 4 }

ipv6PrivTcpConnIfIndex OBJECT-TYPE
   SYNTAX     Ipv6IfIndexOrZero
   MAX-ACCESS read-only
   STATUS     current
   DESCRIPTION
        "An index object used to disambiguate conceptual rows in
         the table, since the connection 4-tuple may not be unique.
         If the connection's remote address (ipv6PrivTcpConnRemAddress)
         is a link-local address and the connection's local address
         (ipv6PrivTcpConnLocalAddress) is not a link-local address, this
         object identifies a local interface on the same link as
         the connection's remote link-local address.
         Otherwise, this object identifies the local interface that
         is associated with the ipv6PrivTcpConnLocalAddress for this
         TCP connection.  If such a local interface cannot be determined,
         this object should take on the value 0.  (A possible example
         of this would be if the value of ipv6PrivTcpConnLocalAddress is ::0.)
         The interface identified by a particular non-0 value of this
         index is the same interface as identified by the same value
         of ipv6PrivIfIndex.
         The value of this object must remain constant during the life
         of the TCP connection."
   ::= { ipv6PrivTcpConnEntry 5 }

ipv6PrivTcpConnState OBJECT-TYPE
   SYNTAX     INTEGER {
        closed(1),
        listen(2),
        synSent(3),
        synReceived(4),
        established(5),
        finWait1(6),
        finWait2(7),
        closeWait(8),
        lastAck(9),
        closing(10),
        timeWait(11),
        deleteTCB(12) }
   MAX-ACCESS read-write
   STATUS     current
   DESCRIPTION
        "The state of this TCP connection.

         The only value which may be set by a management station is
         deleteTCB(12).  Accordingly, it is appropriate for an agent
         to return an error response (`badValue' for SNMPv1, 'wrongValue'
         for SNMPv2) if a management station attempts to set this
         object to any other value.

         If a management station sets this object to the value
         deleteTCB(12), then this has the effect of deleting the TCB
         (as defined in RFC 793) of the corresponding connection on
         the managed node, resulting in immediate termination of the
         connection.

         As an implementation-specific option, a RST segment may be
         sent from the managed node to the other TCP endpoint (note
         however that RST segments are not sent reliably)."
   ::= { ipv6PrivTcpConnEntry 6 }

ipv6PrivUdpTable OBJECT-TYPE
   SYNTAX      SEQUENCE OF Ipv6PrivUdpEntry
   MAX-ACCESS  not-accessible
   STATUS      current
   DESCRIPTION
        "A table containing UDP listener information for
         UDP/IPv6 endpoints."
   ::= {ipv6PrivMIBObjects 14}

ipv6PrivUdpEntry OBJECT-TYPE
   SYNTAX      Ipv6PrivUdpEntry
   MAX-ACCESS  not-accessible
   STATUS      current
   DESCRIPTION
        "Information about a particular current UDP listener.

         Note that conceptual rows in this table require an
         additional index object compared to udpTable, since
         IPv6 addresses are not guaranteed to be unique on the
         managed node."
   INDEX   { ipv6PrivUdpLocalAddress,
             ipv6PrivUdpLocalPort,
             ipv6PrivUdpIfIndex }
   ::= { ipv6PrivUdpTable 1 }

Ipv6PrivUdpEntry ::= SEQUENCE {
   ipv6PrivUdpLocalAddress    Ipv6Address,
   ipv6PrivUdpLocalPort       INTEGER,
   ipv6PrivUdpIfIndex         Ipv6IfIndexOrZero }

ipv6PrivUdpLocalAddress OBJECT-TYPE
   SYNTAX       Ipv6Address
   MAX-ACCESS   read-only
   STATUS       current
   DESCRIPTION
        "The local IPv6 address for this UDP listener.
         In the case of a UDP listener which is willing
         to accept datagrams for any IPv6 address
         associated with the managed node, the value ::0
         is used."
   ::= { ipv6PrivUdpEntry 1 }

ipv6PrivUdpLocalPort OBJECT-TYPE
    SYNTAX     INTEGER (0..65535)
    MAX-ACCESS read-only
    STATUS     current
    DESCRIPTION
        "The local port number for this UDP listener."
    ::= { ipv6PrivUdpEntry 2 }

ipv6PrivUdpIfIndex OBJECT-TYPE
   SYNTAX     Ipv6IfIndexOrZero
   MAX-ACCESS   read-only
   STATUS     current
   DESCRIPTION
        "An index object used to disambiguate conceptual rows in
         the table, since the ipv6PrivUdpLocalAddress/ipv6PrivUdpLocalPort
         pair may not be unique.

         This object identifies the local interface that is
         associated with ipv6PrivUdpLocalAddress for this UDP listener.
         If such a local interface cannot be determined, this object
         should take on the value 0.  (A possible example of this
         would be if the value of ipv6PrivUdpLocalAddress is ::0.)

         The interface identified by a particular non-0 value of
         this index is the same interface as identified by the same
         value of ipv6PrivIfIndex.

         The value of this object must remain constant during
         the life of this UDP endpoint."
   ::= { ipv6PrivUdpEntry 3 }
   
ipv6PrivNeighborStatic   OBJECT-TYPE
             SYNTAX      INTEGER
             MAX-ACCESS  read-only
             STATUS     current
             DESCRIPTION
                "The static ipv6 neighbor number"
              ::= { ipv6PrivMIBObjects 15 }
              
   ipv6PrivNeighborDynamic   OBJECT-TYPE
             SYNTAX      INTEGER
             MAX-ACCESS  read-only
             STATUS     current
             DESCRIPTION
                "The Dynamic ipv6 neighbor number"
              ::= { ipv6PrivMIBObjects 16 }           
    
   ipv6PrivNeighborAge   OBJECT-TYPE
             SYNTAX      INTEGER
             MAX-ACCESS  read-write
             STATUS     current
             DESCRIPTION
                "The neighbor aging time"
              ::= { ipv6PrivMIBObjects 17 }      

	ipv6PrivDADRetransTimes   OBJECT-TYPE
		 SYNTAX      INTEGER
		 MAX-ACCESS  read-write
		 STATUS     current
		 DESCRIPTION
			"The neighbor retrans times"
		  ::= { ipv6PrivMIBObjects 18 } 

	ipv6PrivStaticRouteNum   OBJECT-TYPE
		 SYNTAX      INTEGER
		 MAX-ACCESS  read-write
		 STATUS     current
		 DESCRIPTION
			"The count of static route"
		  ::= { ipv6PrivMIBObjects 19 } 

         -- IPv6 PMTU table

         ipv6PrivPmtuTable OBJECT-TYPE
             SYNTAX     SEQUENCE OF Ipv6PrivPmtuEntry
             MAX-ACCESS not-accessible
             STATUS     current
             DESCRIPTION
               "IPv6 Pmtu table."
             ::= { ipv6PrivMIBObjects 20 }

         ipv6PrivPmtuEntry OBJECT-TYPE
             SYNTAX     Ipv6PrivPmtuEntry
             MAX-ACCESS not-accessible
             STATUS     current
             DESCRIPTION
                     "A pmtu entry."   
             INDEX   {  
             		   ipv6PrivPmtuIfIndex,		
             		   ipv6PrivPmtuDest}
             ::= { ipv6PrivPmtuTable 1 }

         Ipv6PrivPmtuEntry ::= SEQUENCE {   
         	 	 ipv6PrivPmtuIfIndex         Ipv6IfIndexOrZero,
                 ipv6PrivPmtuDest            Ipv6Address,
                 ipv6PrivPmtuExpire      	 Unsigned32,
                 ipv6PrivPmtuMtu          	 Unsigned32                 
             }           
                          
         ipv6PrivPmtuIfIndex OBJECT-TYPE
             SYNTAX     Ipv6IfIndexOrZero
             MAX-ACCESS read-only
             STATUS     current
             DESCRIPTION
               "The index value which uniquely identifies the local
               interface of this pmtu."
             ::= { ipv6PrivPmtuEntry 1 }
         
         ipv6PrivPmtuDest OBJECT-TYPE
             SYNTAX     Ipv6Address
             MAX-ACCESS read-only
             STATUS     current
             DESCRIPTION
               "The destination IPv6 address of this pmtu."
             ::= { ipv6PrivPmtuEntry 2 }

         ipv6PrivPmtuExpire OBJECT-TYPE
             SYNTAX     Unsigned32
             MAX-ACCESS read-only 
             STATUS     current
             DESCRIPTION
               "The expire time of this pmtu."
             ::= { ipv6PrivPmtuEntry 3 }
		
         ipv6PrivPmtuMtu OBJECT-TYPE
             SYNTAX     Unsigned32
             MAX-ACCESS read-only
             STATUS     current
             DESCRIPTION
                "The mtu of this pmtu."
             ::= { ipv6PrivPmtuEntry 4 }

        -- definition of IPv6-related notifications.
        -- Note that we need ipv6PrivNotificationPrefix with the 0
        -- sub-identifier to make this MIB to translate to
        -- an SNMPv1 format in a reversible way. For example
        -- it is needed for proxies that convert SNMPv1 traps
        -- to SNMPv2 notifications without MIB knowledge.

        ipv6PrivNotifications      OBJECT IDENTIFIER
             ::= { wriIPv6 2 }
        ipv6PrivNotificationPrefix OBJECT IDENTIFIER
             ::= { ipv6PrivNotifications 0 }

        ipv6PrivIfStateChange NOTIFICATION-TYPE
             OBJECTS {
                      ipv6PrivIfDescr,
                      ipv6PrivIfOperStatus -- the new state of the If.
                     }
             STATUS             current
             DESCRIPTION
                "An ipv6PrivIfStateChange notification signifies
                that there has been a change in the state of
                an ipv6Priv interface.  This notification should
                be generated when the interface's operational
                status transitions to or from the up(1) state."

             ::= { ipv6PrivNotificationPrefix 1 }


        -- conformance information

        ipv6PrivConformance OBJECT IDENTIFIER ::= { wriIPv6 3 }

        ipv6PrivCompliances OBJECT IDENTIFIER ::= { ipv6PrivConformance 1 }
        ipv6PrivGroups      OBJECT IDENTIFIER ::= { ipv6PrivConformance 2 }

        -- compliance statements
        ipv6PrivCompliance MODULE-COMPLIANCE
            STATUS  current
            DESCRIPTION
              "The compliance statement for SNMPv2 entities which
              implement ipv6Priv MIB."
            MODULE  -- this module
                MANDATORY-GROUPS { ipv6PrivGeneralGroup,
                                   ipv6PrivNotificationGroup }
                  OBJECT    ipv6PrivForwarding
                    MIN-ACCESS  read-only
                    DESCRIPTION
                       "An agent is not required to provide write
                        access to this object"
                  OBJECT    ipv6PrivDefaultHopLimit
                    MIN-ACCESS  read-only
                    DESCRIPTION
                       "An agent is not required to provide write
                        access to this object"
                  OBJECT    ipv6PrivIfDescr
                    MIN-ACCESS  read-only
                    DESCRIPTION
                       "An agent is not required to provide write
                        access to this object"
                  OBJECT    ipv6PrivIfIdentifier
                    MIN-ACCESS  read-only
                    DESCRIPTION
                       "An agent is not required to provide write
                        access to this object"
                  OBJECT    ipv6PrivIfIdentifierLength
                    MIN-ACCESS  read-only
                    DESCRIPTION
                       "An agent is not required to provide write
                        access to this object"

                  OBJECT    ipv6PrivIfAdminStatus
                    MIN-ACCESS  read-only
                    DESCRIPTION
                       "An agent is not required to provide write
                        access to this object"
                  OBJECT    ipv6PrivRouteValid
                    MIN-ACCESS  read-only
                    DESCRIPTION
                       "An agent is not required to provide write
                        access to this object"
                  OBJECT    ipv6PrivNetToMediaValid
                    MIN-ACCESS  read-only
                    DESCRIPTION
                       "An agent is not required to provide write
                        access to this object"
            ::= { ipv6PrivCompliances 1 }

        ipv6PrivGeneralGroup OBJECT-GROUP
            OBJECTS { ipv6PrivForwarding,
                      ipv6PrivDefaultHopLimit,
                      ipv6PrivInterfaces,
                      ipv6PrivIfTableLastChange,
                      ipv6PrivIfDescr,
                      ipv6PrivIfLowerLayer,
                      ipv6PrivIfEffectiveMtu,
                      ipv6PrivIfReasmMaxSize,
                      ipv6PrivIfIdentifier,
                      ipv6PrivIfIdentifierLength,
                      ipv6PrivIfPhysicalAddress,
                      ipv6PrivIfAdminStatus,
                      ipv6PrivIfOperStatus,
                      ipv6PrivIfLastChange,
                      ipv6PrivIfStatsInReceives,
                      ipv6PrivIfStatsInHdrErrors,
                      ipv6PrivIfStatsInTooBigErrors,
                      ipv6PrivIfStatsInNoRoutes,
                      ipv6PrivIfStatsInAddrErrors,
                      ipv6PrivIfStatsInUnknownProtos,
                      ipv6PrivIfStatsInTruncatedPkts,
                      ipv6PrivIfStatsInDiscards,
                      ipv6PrivIfStatsInDelivers,
                      ipv6PrivIfStatsOutForwDatagrams,
                      ipv6PrivIfStatsOutRequests,
                      ipv6PrivIfStatsOutDiscards,
                      ipv6PrivIfStatsOutFragOKs,
                      ipv6PrivIfStatsOutFragFails,
                      ipv6PrivIfStatsOutFragCreates,
                      ipv6PrivIfStatsReasmReqds,
                      ipv6PrivIfStatsReasmOKs,
                      ipv6PrivIfStatsReasmFails,
                      ipv6PrivIfStatsInMcastPkts,
                      ipv6PrivIfStatsOutMcastPkts,
                      ipv6PrivAddrPrefixOnLinkFlag,
                      ipv6PrivAddrPrefixAutonomousFlag,
                      ipv6PrivAddrPrefixAdvPreferredLifetime,
                      ipv6PrivAddrPrefixAdvValidLifetime,
                      ipv6PrivAddrPfxLength,
                      ipv6PrivAddrType,
                      ipv6PrivAddrAnycastFlag,
                      ipv6PrivAddrStatus,
                      ipv6PrivRouteNumber,
                      ipv6PrivDiscardedRoutes,
                      ipv6PrivRouteIfIndex,
                      ipv6PrivRouteNextHop,
                      ipv6PrivRouteType,
                      ipv6PrivRouteProtocol,
                      ipv6PrivRoutePolicy,
                      ipv6PrivRouteAge,
                      ipv6PrivRouteNextHopRDI,
                      ipv6PrivRouteMetric,
                      ipv6PrivRouteWeight,
                      ipv6PrivRouteInfo,
                      ipv6PrivRouteValid,
                      ipv6PrivNetToMediaPhysAddress,
                      ipv6PrivNetToMediaType,
                      ipv6PrivIfNetToMediaState,
                      ipv6PrivIfNetToMediaLastUpdated,
                      ipv6PrivNetToMediaValid }
            STATUS    current
            DESCRIPTION
                 "The IPv6 group of objects providing for basic
                  management of IPv6 entities."
            ::= { ipv6PrivGroups 1 }

        ipv6PrivNotificationGroup NOTIFICATION-GROUP
            NOTIFICATIONS { ipv6PrivIfStateChange }
            STATUS    current
            DESCRIPTION
                 "The notification that an IPv6 entity is required
                  to implement."


            ::= { ipv6PrivGroups 2 }

         END
