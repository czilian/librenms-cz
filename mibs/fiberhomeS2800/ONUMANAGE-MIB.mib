--
-- onuManage.mib
-- MIB generated by MG-SOFT Visual MIB Builder Version 6.0  Build 88
-- Thursday, June 14, 2012 at 16:43:28
--

	ONUMANAGE-MIB DEFINITIONS ::= BEGIN
 
		IMPORTS
			mib-2			
				FROM RFC1213-MIB			
			enterprises, Integer32, Unsigned32, OBJECT-TYPE, MODULE-IDENTITY, 
			NOTIFICATION-TYPE			
				FROM SNMPv2-SMI			
			TEXTUAL-CONVENTION			
				FROM SNMPv2-TC;
	
	
		wri MODULE-IDENTITY 
			LAST-UPDATED ""		-- 
			ORGANIZATION 
				"FiberHome Networks Systems, Inc."
			CONTACT-INFO 
				"http://www.fhn.com.cn"
			DESCRIPTION 
				"The Structure of Management Information for the FHN enterprise."
			::= { enterprises 3807 }

		
	
--
-- Textual conventions
--
	
		InterfaceIndex ::= TEXTUAL-CONVENTION
			STATUS current
			DESCRIPTION 
				"The range of ifIndex."
			SYNTAX Integer32

	
--
-- Node definitions
--
	
		wriProtocol OBJECT IDENTIFIER ::= { wri 2 }

		
		onuManage OBJECT IDENTIFIER ::= { wriProtocol 1511 }

		
		onuGlobalConfig OBJECT IDENTIFIER ::= { onuManage 1 }

		
		onuGlobalConfirm OBJECT-TYPE
			SYNTAX OCTET STRING
			MAX-ACCESS read-write
			STATUS current
			DESCRIPTION
				"The global debug switch."
			::= { onuGlobalConfig 1 }

		
		onuGlobalNoAuthMove OBJECT-TYPE
			SYNTAX INTEGER
				{
				enable(1),
				disable(2)
				}
			MAX-ACCESS read-write
			STATUS current
			DESCRIPTION
				"The global debug switch."
			::= { onuGlobalConfig 2 }

		
		onuGlobalMatchCap OBJECT-TYPE
			SYNTAX INTEGER
				{
				yes(0),
				no(1)
				}
			MAX-ACCESS read-write
			STATUS current
			DESCRIPTION
				"The global debug switch."
			::= { onuGlobalConfig 3 }

		
		onuGlobalRegOnuNum OBJECT-TYPE
			SYNTAX Unsigned32
			MAX-ACCESS read-only
			STATUS current
			DESCRIPTION
				"The global debug switch."
			::= { onuGlobalConfig 4 }

		
		onuGlobalAuthOnuNum OBJECT-TYPE
			SYNTAX Unsigned32
			MAX-ACCESS read-only
			STATUS current
			DESCRIPTION
				"The global debug switch."
			::= { onuGlobalConfig 5 }

		
		onuRegisterTable OBJECT-TYPE
			SYNTAX SEQUENCE OF OnuRegisterEntry
			MAX-ACCESS not-accessible
			STATUS current
			DESCRIPTION
				"Information describing the configured  parame-
				ters  and cumulative statistics of the router's
				attached areas."
			::= { onuManage 2 }

		
		onuRegisterEntry OBJECT-TYPE
			SYNTAX OnuRegisterEntry
			MAX-ACCESS not-accessible
			STATUS current
			DESCRIPTION
				"The entry of 'onuRegisterTable'."
			INDEX { onuRegIfindex, onuRegPhysicalIdIdx }
			::= { onuRegisterTable 1 }

		
		OnuRegisterEntry ::=
			SEQUENCE { 
				onuRegIfindex
					InterfaceIndex,
				onuRegPhysicalIdIdx
					OCTET STRING,
				onuRegOnuPhyType
					INTEGER,
				onuRegLoid
					OCTET STRING,
				onuRegLoidPassword
					OCTET STRING,
				onuRegPhysicalPassword
					OCTET STRING,
				onuRegOnuAuthId
					Unsigned32,
				onuRegOnuAuthStatus
					INTEGER,
				onuRegOnuType
					Integer32,
				onuRegOnuMngMode
					INTEGER,
				onuRegOnuBatteryBackup
					INTEGER,
				onuRegOnuChipVendorId
					Integer32,
				onuRegOnuChipSetId
					Integer32,
				onuRegOnuChipRevision
					Integer32,
				onuRegOnuChipDate
					OCTET STRING,
				onuRegOnuVendorId
					OCTET STRING,
				onuRegOnuModel
					OCTET STRING,
				onuRegOnuHwVersion
					OCTET STRING,
				onuRegOnuSwVersion
					OCTET STRING,
				onuRegOnuFirmwareVersion
					OCTET STRING,
				onuRegCtcExtVer
					Integer32,
				onuRegIpAddrMode
					INTEGER,
				onuReg1GUplinkPortNum
					Integer32,
				onuReg10GUplinkPortNum
					Integer32,
				onuRegPotsPortNum
					Integer32,
				onuRegGEPortNum
					Integer32,
				onuRegFEPortNum
					Integer32,
				onuRegE1PortNum
					Integer32,
				onuRegT1PortNum
					Integer32,
				onuRegMoCAPortNum
					Integer32,
				onuRegEOCPortNum
					Integer32,
				onuRegWiFiPortNum
					Integer32,
				onuRegCATVPortNum
					Integer32,
				onuRegClock1588PortNum
					Integer32,
				onuRegRSPortNum
					Integer32,
				onuRegADSLPortNum
					Integer32,
				onuRegVDSLPortNum
					Integer32,
				onuRegUSBPortNum
					Integer32,
				onuRegUser1Type
					Integer32,
				onuRegUser1Num
					Integer32,
				onuRegUser2Type
					Integer32,
				onuRegUser2Num
					Integer32,
				onuRegLlidNum
					Integer32,
				onuRegOnuWorkMode
					INTEGER,
				onuRegOnuOamSupport
					INTEGER,
				onuRegLinkMac
					OCTET STRING,
				onuRegTContNum
					Integer32,
				onuRegGemPortNum
					Integer32,
				onuRegOnuCtcDevType
					Integer32,
				onuRegOpticProtectType
					INTEGER,
				onuRegIpv6Support
					INTEGER,
				onuRegPowerControl
					INTEGER,
				onuRegSrvSlotNum
					Integer32,
				onuRegSupportLlidNum
					Unsigned32,
				onuRegOnlineLlidNum
					Unsigned32,
				onuRegReRegister
					INTEGER,
				onuRegForceShutdown
					INTEGER
			 }

		onuRegIfindex OBJECT-TYPE
			SYNTAX InterfaceIndex
			MAX-ACCESS read-only
			STATUS current
			DESCRIPTION
				"The interface index."
			::= { onuRegisterEntry 1 }

		
		onuRegPhysicalIdIdx OBJECT-TYPE
			SYNTAX OCTET STRING (SIZE (12))
			MAX-ACCESS read-only
			STATUS current
			DESCRIPTION
				"MAC address(epon) / physical SN(gpon)."
			::= { onuRegisterEntry 2 }

		
		onuRegOnuPhyType OBJECT-TYPE
			SYNTAX INTEGER
				{
				epon(0),
				gpon(1)
				}
			MAX-ACCESS read-only
			STATUS current
			DESCRIPTION
				"The physical type of the ONU."
			::= { onuRegisterEntry 3 }

		
		onuRegLoid OBJECT-TYPE
			SYNTAX OCTET STRING (SIZE (0..24))
			MAX-ACCESS read-only
			STATUS current
			DESCRIPTION
				"The logical SN ID of the ONU."
			::= { onuRegisterEntry 4 }

		
		onuRegLoidPassword OBJECT-TYPE
			SYNTAX OCTET STRING (SIZE (0..12))
			MAX-ACCESS read-only
			STATUS current
			DESCRIPTION
				"The LOID password."
			::= { onuRegisterEntry 5 }

		
		onuRegPhysicalPassword OBJECT-TYPE
			SYNTAX OCTET STRING (SIZE (0..10))
			MAX-ACCESS read-only
			STATUS current
			DESCRIPTION
				"The physical password."
			::= { onuRegisterEntry 6 }

		
		onuRegOnuAuthId OBJECT-TYPE
			SYNTAX Unsigned32
			MAX-ACCESS read-only
			STATUS current
			DESCRIPTION
				"The authorization number of the ONU.
				Note: If the ONU is not authorized, '0' or '0xffff' will be returned."
			::= { onuRegisterEntry 7 }

		
		onuRegOnuAuthStatus OBJECT-TYPE
			SYNTAX INTEGER
				{
				unauth(0),
				auth(1),
				illegal(2)
				}
			MAX-ACCESS read-only
			STATUS current
			DESCRIPTION
				"The ONU is authorized or not."
			::= { onuRegisterEntry 8 }

		
		onuRegOnuType OBJECT-TYPE
			SYNTAX Integer32
			MAX-ACCESS read-only
			STATUS current
			DESCRIPTION
				"The type of the ONU."
			::= { onuRegisterEntry 9 }

		
		onuRegOnuMngMode OBJECT-TYPE
			SYNTAX INTEGER
				{
				default(0),
				snmp(1),
				other(2)
				}
			MAX-ACCESS read-only
			STATUS current
			DESCRIPTION
				"The ONU is managed by SNMP or via OLT. 
				For epon, default means 'oam'. 
				For gpon, default means 'omci'."
			::= { onuRegisterEntry 10 }

		
		onuRegOnuBatteryBackup OBJECT-TYPE
			SYNTAX INTEGER
				{
				yes(1),
				no(2)
				}
			MAX-ACCESS read-only
			STATUS current
			DESCRIPTION
				"The backup battery is equipped or not."
			::= { onuRegisterEntry 11 }

		
		onuRegOnuChipVendorId OBJECT-TYPE
			SYNTAX Integer32
			MAX-ACCESS read-only
			STATUS current
			DESCRIPTION
				"The chip vendor ID."
			::= { onuRegisterEntry 12 }

		
		onuRegOnuChipSetId OBJECT-TYPE
			SYNTAX Integer32
			MAX-ACCESS read-only
			STATUS current
			DESCRIPTION
				"The chip set ID."
			::= { onuRegisterEntry 13 }

		
		onuRegOnuChipRevision OBJECT-TYPE
			SYNTAX Integer32
			MAX-ACCESS read-only
			STATUS current
			DESCRIPTION
				"The revision information of the chip."
			::= { onuRegisterEntry 14 }

		
		onuRegOnuChipDate OBJECT-TYPE
			SYNTAX OCTET STRING (SIZE (10))
			MAX-ACCESS read-only
			STATUS current
			DESCRIPTION
				"The date when the chip is designed."
			::= { onuRegisterEntry 15 }

		
		onuRegOnuVendorId OBJECT-TYPE
			SYNTAX OCTET STRING (SIZE (0..4))
			MAX-ACCESS read-only
			STATUS current
			DESCRIPTION
				"The ONU vendor ID."
			::= { onuRegisterEntry 16 }

		
		onuRegOnuModel OBJECT-TYPE
			SYNTAX OCTET STRING (SIZE (0..4))
			MAX-ACCESS read-only
			STATUS current
			DESCRIPTION
				"The ONU model."
			::= { onuRegisterEntry 17 }

		
		onuRegOnuHwVersion OBJECT-TYPE
			SYNTAX OCTET STRING (SIZE (0..8))
			MAX-ACCESS read-only
			STATUS current
			DESCRIPTION
				"The hardware version of the ONU."
			::= { onuRegisterEntry 18 }

		
		onuRegOnuSwVersion OBJECT-TYPE
			SYNTAX OCTET STRING (SIZE (0..16))
			MAX-ACCESS read-only
			STATUS current
			DESCRIPTION
				"The software version of the ONU."
			::= { onuRegisterEntry 19 }

		
		onuRegOnuFirmwareVersion OBJECT-TYPE
			SYNTAX OCTET STRING
			MAX-ACCESS read-only
			STATUS current
			DESCRIPTION
				"The firmware version of the ONU."
			::= { onuRegisterEntry 20 }

		
		onuRegCtcExtVer OBJECT-TYPE
			SYNTAX Integer32
			MAX-ACCESS read-only
			STATUS current
			DESCRIPTION
				"The ctc version.
				
				value  version
				--------------
				0      2.0
				1      2.1"
			::= { onuRegisterEntry 21 }

		
		onuRegIpAddrMode OBJECT-TYPE
			SYNTAX INTEGER
				{
				support(1),
				notsupport(2),
				dhcponly(3),
				staticonly(4)
				}
			MAX-ACCESS read-only
			STATUS current
			DESCRIPTION
				"The IP address mode."
			::= { onuRegisterEntry 22 }

		
		onuReg1GUplinkPortNum OBJECT-TYPE
			SYNTAX Integer32 (1..2)
			MAX-ACCESS read-only
			STATUS current
			DESCRIPTION
				"The number of 1G uplink ports."
			::= { onuRegisterEntry 23 }

		
		onuReg10GUplinkPortNum OBJECT-TYPE
			SYNTAX Integer32 (0..2)
			MAX-ACCESS read-only
			STATUS current
			DESCRIPTION
				"The number of 10G uplink ports."
			::= { onuRegisterEntry 24 }

		
		onuRegPotsPortNum OBJECT-TYPE
			SYNTAX Integer32 (0..32)
			MAX-ACCESS read-only
			STATUS current
			DESCRIPTION
				"The number of pots ports."
			::= { onuRegisterEntry 25 }

		
		onuRegGEPortNum OBJECT-TYPE
			SYNTAX Integer32 (0..32)
			MAX-ACCESS read-only
			STATUS current
			DESCRIPTION
				"The number of GE ports."
			::= { onuRegisterEntry 26 }

		
		onuRegFEPortNum OBJECT-TYPE
			SYNTAX Integer32 (0..32)
			MAX-ACCESS read-only
			STATUS current
			DESCRIPTION
				"The number of FE ports."
			::= { onuRegisterEntry 27 }

		
		onuRegE1PortNum OBJECT-TYPE
			SYNTAX Integer32 (0..8)
			MAX-ACCESS read-only
			STATUS current
			DESCRIPTION
				"The number of E1 ports."
			::= { onuRegisterEntry 28 }

		
		onuRegT1PortNum OBJECT-TYPE
			SYNTAX Integer32 (0..8)
			MAX-ACCESS read-only
			STATUS current
			DESCRIPTION
				"The number of T1 ports."
			::= { onuRegisterEntry 29 }

		
		onuRegMoCAPortNum OBJECT-TYPE
			SYNTAX Integer32 (0..8)
			MAX-ACCESS read-only
			STATUS current
			DESCRIPTION
				"The number of MoCA ports."
			::= { onuRegisterEntry 30 }

		
		onuRegEOCPortNum OBJECT-TYPE
			SYNTAX Integer32 (0..8)
			MAX-ACCESS read-only
			STATUS current
			DESCRIPTION
				"The number of EOC ports."
			::= { onuRegisterEntry 31 }

		
		onuRegWiFiPortNum OBJECT-TYPE
			SYNTAX Integer32 (0..8)
			MAX-ACCESS read-only
			STATUS current
			DESCRIPTION
				"The number of WiFi ports."
			::= { onuRegisterEntry 32 }

		
		onuRegCATVPortNum OBJECT-TYPE
			SYNTAX Integer32 (0..2)
			MAX-ACCESS read-only
			STATUS current
			DESCRIPTION
				"The number of CATV ports."
			::= { onuRegisterEntry 33 }

		
		onuRegClock1588PortNum OBJECT-TYPE
			SYNTAX Integer32 (0..2)
			MAX-ACCESS read-only
			STATUS current
			DESCRIPTION
				"The number of 1588 clock ports."
			::= { onuRegisterEntry 34 }

		
		onuRegRSPortNum OBJECT-TYPE
			SYNTAX Integer32 (0..8)
			MAX-ACCESS read-only
			STATUS current
			DESCRIPTION
				"The number of RS ports."
			::= { onuRegisterEntry 35 }

		
		onuRegADSLPortNum OBJECT-TYPE
			SYNTAX Integer32 (0..2)
			MAX-ACCESS read-only
			STATUS current
			DESCRIPTION
				"The number of ADSL ports."
			::= { onuRegisterEntry 36 }

		
		onuRegVDSLPortNum OBJECT-TYPE
			SYNTAX Integer32 (0..2)
			MAX-ACCESS read-only
			STATUS current
			DESCRIPTION
				"The number of VDSL ports."
			::= { onuRegisterEntry 37 }

		
		onuRegUSBPortNum OBJECT-TYPE
			SYNTAX Integer32 (0..2)
			MAX-ACCESS read-only
			STATUS current
			DESCRIPTION
				"The number of USB ports."
			::= { onuRegisterEntry 38 }

		
		onuRegUser1Type OBJECT-TYPE
			SYNTAX Integer32
			MAX-ACCESS read-only
			STATUS current
			DESCRIPTION
				"The type of user-defined port 1."
			::= { onuRegisterEntry 39 }

		
		onuRegUser1Num OBJECT-TYPE
			SYNTAX Integer32 (0..8)
			MAX-ACCESS read-only
			STATUS current
			DESCRIPTION
				"The number of user-defined port 1."
			::= { onuRegisterEntry 40 }

		
		onuRegUser2Type OBJECT-TYPE
			SYNTAX Integer32
			MAX-ACCESS read-only
			STATUS current
			DESCRIPTION
				"The type of user-defined port 2."
			::= { onuRegisterEntry 41 }

		
		onuRegUser2Num OBJECT-TYPE
			SYNTAX Integer32 (0..8)
			MAX-ACCESS read-only
			STATUS current
			DESCRIPTION
				"The number of user-defined port 2."
			::= { onuRegisterEntry 42 }

		
		onuRegLlidNum OBJECT-TYPE
			SYNTAX Integer32 (1..8)
			MAX-ACCESS read-only
			STATUS current
			DESCRIPTION
				"The number of LLID."
			::= { onuRegisterEntry 43 }

		
		onuRegOnuWorkMode OBJECT-TYPE
			SYNTAX INTEGER
				{
				single(0),
				multi(1)
				}
			MAX-ACCESS read-only
			STATUS current
			DESCRIPTION
				"The work mode of the ONU.
				Note: This leaf is for epon."
			::= { onuRegisterEntry 44 }

		
		onuRegOnuOamSupport OBJECT-TYPE
			SYNTAX INTEGER
				{
				notsupport(0),
				support(1)
				}
			MAX-ACCESS read-only
			STATUS current
			DESCRIPTION
				"OAM is supported or not.
				Note: This leaf is for epon."
			::= { onuRegisterEntry 45 }

		
		onuRegLinkMac OBJECT-TYPE
			SYNTAX OCTET STRING (SIZE (48))
			MAX-ACCESS read-only
			STATUS current
			DESCRIPTION
				"The MAC addresses of all ONU link.
				Note: This leaf is for epon."
			::= { onuRegisterEntry 46 }

		
		onuRegTContNum OBJECT-TYPE
			SYNTAX Integer32 (1..32 | 65535)
			MAX-ACCESS read-only
			STATUS current
			DESCRIPTION
				"The number of tCont.
				Note: This leaf is for gpon."
			::= { onuRegisterEntry 47 }

		
		onuRegGemPortNum OBJECT-TYPE
			SYNTAX Integer32 (1..4096)
			MAX-ACCESS read-only
			STATUS current
			DESCRIPTION
				"The number of gem port.
				Note: This leaf is for gpon."
			::= { onuRegisterEntry 48 }

		
		onuRegOnuCtcDevType OBJECT-TYPE
			SYNTAX Integer32
			MAX-ACCESS read-only
			STATUS current
			DESCRIPTION
				"The type of the ONU."
			::= { onuRegisterEntry 49 }

		
		onuRegOpticProtectType OBJECT-TYPE
			SYNTAX INTEGER
				{
				none(0),
				typec(1),
				typed(2)
				}
			MAX-ACCESS read-only
			STATUS current
			DESCRIPTION
				"The type of the ONU."
			::= { onuRegisterEntry 50 }

		
		onuRegIpv6Support OBJECT-TYPE
			SYNTAX INTEGER
				{
				notsupport(0),
				support(1)
				}
			MAX-ACCESS read-only
			STATUS current
			DESCRIPTION
				"The type of the ONU."
			::= { onuRegisterEntry 51 }

		
		onuRegPowerControl OBJECT-TYPE
			SYNTAX INTEGER
				{
				notsupport(0),
				support(1)
				}
			MAX-ACCESS read-only
			STATUS current
			DESCRIPTION
				"The type of the ONU."
			::= { onuRegisterEntry 52 }

		
		onuRegSrvSlotNum OBJECT-TYPE
			SYNTAX Integer32
			MAX-ACCESS read-only
			STATUS current
			DESCRIPTION
				"The type of the ONU."
			::= { onuRegisterEntry 53 }

		
		onuRegSupportLlidNum OBJECT-TYPE
			SYNTAX Unsigned32
			MAX-ACCESS read-only
			STATUS current
			DESCRIPTION
				"The max llid number supported."
			::= { onuRegisterEntry 54 }

		
		onuRegOnlineLlidNum OBJECT-TYPE
			SYNTAX Unsigned32
			MAX-ACCESS read-only
			STATUS current
			DESCRIPTION
				"The online llid number."
			::= { onuRegisterEntry 55 }

		
		onuRegReRegister OBJECT-TYPE
			SYNTAX INTEGER { reregister(1) }
			MAX-ACCESS read-write
			STATUS current
			DESCRIPTION
				"The online llid number."
			::= { onuRegisterEntry 56 }

		
		onuRegForceShutdown OBJECT-TYPE
			SYNTAX INTEGER { forceshutdown(1) }
			MAX-ACCESS read-write
			STATUS current
			DESCRIPTION
				"Description."
			::= { onuRegisterEntry 57 }

		
		onuAuthTable OBJECT-TYPE
			SYNTAX SEQUENCE OF OnuAuthEntry
			MAX-ACCESS not-accessible
			STATUS current
			DESCRIPTION
				"The list of Hosts, and their metrics, that the
				router will advertise as host routes."
			::= { onuManage 3 }

		
		onuAuthEntry OBJECT-TYPE
			SYNTAX OnuAuthEntry
			MAX-ACCESS not-accessible
			STATUS current
			DESCRIPTION
				"The entry of 'onuAuthConfigTable'."
			INDEX { onuAuthIfindex, onuAuthOnuId }
			::= { onuAuthTable 1 }

		
		OnuAuthEntry ::=
			SEQUENCE { 
				onuAuthIfindex
					InterfaceIndex,
				onuAuthOnuId
					Integer32,
				onuAuthEntryStatus
					Integer32,
				onuAuthSlot
					Unsigned32,
				onuAuthPort
					Unsigned32,
				onuAuthPonType
					INTEGER,
				onuAuthPhyId
					OCTET STRING,
				onuAuthPhyPassword
					OCTET STRING,
				onuAuthLoid
					OCTET STRING,
				onuAuthLoidPassword
					OCTET STRING,
				onuAuthOnlineStatus
					INTEGER,
				onuAuthOnuType
					Integer32,
				onuAuthCapIdx
					Integer32,
				onuAuthOperActive
					INTEGER,
				onuAuthAdminActive
					INTEGER,
				onuAuthAuthMode
					INTEGER,
				onuAuthPreCfg
					Integer32,
				onuAuthPswOnce
					INTEGER,
				onuAuthAgingTime
					Integer32,
				onuAuthAgingStatus
					INTEGER,
				onuAuthManageMode
					INTEGER,
				onuAuthHwVersion
					OCTET STRING,
				onuAuthSwVersion
					OCTET STRING,
				onuAuthConfigErr
					Integer32
			 }

		onuAuthIfindex OBJECT-TYPE
			SYNTAX InterfaceIndex
			MAX-ACCESS read-only
			STATUS current
			DESCRIPTION
				"The interface index."
			::= { onuAuthEntry 1 }

		
		onuAuthOnuId OBJECT-TYPE
			SYNTAX Integer32 (1..256)
			MAX-ACCESS read-only
			STATUS current
			DESCRIPTION
				"The ONU ID."
			::= { onuAuthEntry 2 }

		
		onuAuthEntryStatus OBJECT-TYPE
			SYNTAX Integer32
			MAX-ACCESS read-write
			STATUS current
			DESCRIPTION
				"Description."
			::= { onuAuthEntry 3 }

		
		onuAuthSlot OBJECT-TYPE
			SYNTAX Unsigned32
			MAX-ACCESS read-only
			STATUS current
			DESCRIPTION
				"The slot number."
			::= { onuAuthEntry 4 }

		
		onuAuthPort OBJECT-TYPE
			SYNTAX Unsigned32
			MAX-ACCESS read-only
			STATUS current
			DESCRIPTION
				"The port number."
			::= { onuAuthEntry 5 }

		
		onuAuthPonType OBJECT-TYPE
			SYNTAX INTEGER
				{
				epon(0),
				gpon(1)
				}
			MAX-ACCESS read-only
			STATUS current
			DESCRIPTION
				"The physical type of the ONU."
			::= { onuAuthEntry 6 }

		
		onuAuthPhyId OBJECT-TYPE
			SYNTAX OCTET STRING (SIZE (6..12))
			MAX-ACCESS read-write
			STATUS current
			DESCRIPTION
				"The physical ID of the ONU."
			::= { onuAuthEntry 7 }

		
		onuAuthPhyPassword OBJECT-TYPE
			SYNTAX OCTET STRING (SIZE (0..10))
			MAX-ACCESS read-write
			STATUS current
			DESCRIPTION
				"The physical password."
			::= { onuAuthEntry 8 }

		
		onuAuthLoid OBJECT-TYPE
			SYNTAX OCTET STRING (SIZE (0..24))
			MAX-ACCESS read-write
			STATUS current
			DESCRIPTION
				"The logical SN ID of the ONU."
			::= { onuAuthEntry 9 }

		
		onuAuthLoidPassword OBJECT-TYPE
			SYNTAX OCTET STRING (SIZE (0..12))
			MAX-ACCESS read-write
			STATUS current
			DESCRIPTION
				"The LOID password."
			::= { onuAuthEntry 10 }

		
		onuAuthOnlineStatus OBJECT-TYPE
			SYNTAX INTEGER
				{
				offline(0),
				online(1)
				}
			MAX-ACCESS read-only
			STATUS current
			DESCRIPTION
				"The status of the ONU is online or offline."
			::= { onuAuthEntry 11 }

		
		onuAuthOnuType OBJECT-TYPE
			SYNTAX Integer32
			MAX-ACCESS read-write
			STATUS current
			DESCRIPTION
				"The onu type."
			::= { onuAuthEntry 12 }

		
		onuAuthCapIdx OBJECT-TYPE
			SYNTAX Integer32 (1..384)
			MAX-ACCESS read-write
			STATUS current
			DESCRIPTION
				"The capability profile number."
			::= { onuAuthEntry 13 }

		
		onuAuthOperActive OBJECT-TYPE
			SYNTAX INTEGER
				{
				enable(1),
				disable(2)
				}
			MAX-ACCESS read-only
			STATUS current
			DESCRIPTION
				"Description."
			::= { onuAuthEntry 14 }

		
		onuAuthAdminActive OBJECT-TYPE
			SYNTAX INTEGER
				{
				enable(1),
				disable(2)
				}
			MAX-ACCESS read-write
			STATUS current
			DESCRIPTION
				"Description."
			::= { onuAuthEntry 15 }

		
		onuAuthAuthMode OBJECT-TYPE
			SYNTAX INTEGER
				{
				phyid(0),
				phyidphypwd(1),
				phypwd(2),
				loidlogicalpwd(3),
				loid(4),
				logicalpwd(5)
				}
			MAX-ACCESS read-write
			STATUS current
			DESCRIPTION
				"Description."
			::= { onuAuthEntry 16 }

		
		onuAuthPreCfg OBJECT-TYPE
			SYNTAX Integer32
			MAX-ACCESS read-only
			STATUS current
			DESCRIPTION
				"Description."
			::= { onuAuthEntry 17 }

		
		onuAuthPswOnce OBJECT-TYPE
			SYNTAX INTEGER
				{
				always(0),
				once(1)
				}
			MAX-ACCESS read-write
			STATUS current
			DESCRIPTION
				"Description."
			::= { onuAuthEntry 18 }

		
		onuAuthAgingTime OBJECT-TYPE
			SYNTAX Integer32 (0..168)
			MAX-ACCESS read-write
			STATUS current
			DESCRIPTION
				"Description."
			::= { onuAuthEntry 19 }

		
		onuAuthAgingStatus OBJECT-TYPE
			SYNTAX INTEGER
				{
				aging(0),
				aged(1)
				}
			MAX-ACCESS read-only
			STATUS current
			DESCRIPTION
				"Description."
			::= { onuAuthEntry 20 }

		
		onuAuthManageMode OBJECT-TYPE
			SYNTAX INTEGER
				{
				default(0),
				snmp(1),
				other(2)
				}
			MAX-ACCESS read-write
			STATUS current
			DESCRIPTION
				"The ONU is managed by SNMP or via OLT. 
				For epon, default means 'oam'. 
				For gpon, default means 'omci'."
			::= { onuAuthEntry 21 }

		
		onuAuthHwVersion OBJECT-TYPE
			SYNTAX OCTET STRING (SIZE (0..8))
			MAX-ACCESS read-only
			STATUS current
			DESCRIPTION
				"The hardware version of the ONU."
			::= { onuAuthEntry 22 }

		
		onuAuthSwVersion OBJECT-TYPE
			SYNTAX OCTET STRING (SIZE (0..16))
			MAX-ACCESS read-only
			STATUS current
			DESCRIPTION
				"The software version of the ONU."
			::= { onuAuthEntry 23 }

		
		onuAuthConfigErr OBJECT-TYPE
			SYNTAX Integer32
			MAX-ACCESS read-only
			STATUS current
			DESCRIPTION
				"Description."
			::= { onuAuthEntry 24 }

		
		onuCapabilityTable OBJECT-TYPE
			SYNTAX SEQUENCE OF OnuCapabilityEntry
			MAX-ACCESS not-accessible
			STATUS current
			DESCRIPTION
				"This table is used to configure the capability profile."
			::= { onuManage 4 }

		
		onuCapabilityEntry OBJECT-TYPE
			SYNTAX OnuCapabilityEntry
			MAX-ACCESS not-accessible
			STATUS current
			DESCRIPTION
				"The entry of 'onuCapabilityTable'."
			INDEX { onuCapIdx }
			::= { onuCapabilityTable 1 }

		
		OnuCapabilityEntry ::=
			SEQUENCE { 
				onuCapIdx
					Integer32,
				onuCapEntryStatus
					INTEGER,
				onuCapName
					OCTET STRING,
				onuCapPonType
					INTEGER,
				onuCap1GUplinkPortNum
					Integer32,
				onuCap10GUplinkPortNum
					Integer32,
				onuCapPotsPortNum
					Integer32,
				onuCapLanPortNum
					Integer32,
				onuCapE1PortNum
					Integer32,
				onuCapT1PortNum
					Integer32,
				onuCapMoCAPortNum
					Integer32,
				onuCapEOCPortNum
					Integer32,
				onuCapWiFiPortNum
					Integer32,
				onuCapCATVPortNum
					Integer32,
				onuCapClock1588PortNum
					Integer32,
				onuCapRSPortNum
					Integer32,
				onuCapADSLPortNum
					Integer32,
				onuCapVDSLPortNum
					Integer32,
				onuCapUSBPortNum
					Integer32,
				onuCapWanPortNum
					Integer32,
				onuCapUser1Type
					Integer32,
				onuCapUser1Num
					Integer32,
				onuCapUser2Type
					Integer32,
				onuCapUser2Num
					Integer32,
				onuCapOnuType
					Integer32,
				onuCapIsBound
					INTEGER,
				onuCapProfileStatusType
					INTEGER
			 }

		onuCapIdx OBJECT-TYPE
			SYNTAX Integer32 (1..384)
			MAX-ACCESS read-only
			STATUS current
			DESCRIPTION
				"The SN number of the profile."
			::= { onuCapabilityEntry 1 }

		
		onuCapEntryStatus OBJECT-TYPE
			SYNTAX INTEGER
				{
				valid(1),
				createrequest(2),
				invalid(4)
				}
			MAX-ACCESS read-write
			STATUS current
			DESCRIPTION
				"The status of the entry."
			::= { onuCapabilityEntry 2 }

		
		onuCapName OBJECT-TYPE
			SYNTAX OCTET STRING (SIZE (1..32))
			MAX-ACCESS read-write
			STATUS current
			DESCRIPTION
				"The name of the profile."
			::= { onuCapabilityEntry 3 }

		
		onuCapPonType OBJECT-TYPE
			SYNTAX INTEGER
				{
				epon(0),
				gpon(1)
				}
			MAX-ACCESS read-write
			STATUS current
			DESCRIPTION
				"The uplink port type."
			::= { onuCapabilityEntry 4 }

		
		onuCap1GUplinkPortNum OBJECT-TYPE
			SYNTAX Integer32 (0..2)
			MAX-ACCESS read-write
			STATUS current
			DESCRIPTION
				"The number of 1G uplink ports."
			::= { onuCapabilityEntry 5 }

		
		onuCap10GUplinkPortNum OBJECT-TYPE
			SYNTAX Integer32 (0..2)
			MAX-ACCESS read-write
			STATUS current
			DESCRIPTION
				"The number of 10G uplink ports."
			::= { onuCapabilityEntry 6 }

		
		onuCapPotsPortNum OBJECT-TYPE
			SYNTAX Integer32 (0..32)
			MAX-ACCESS read-write
			STATUS current
			DESCRIPTION
				"The number of pots ports."
			::= { onuCapabilityEntry 7 }

		
		onuCapLanPortNum OBJECT-TYPE
			SYNTAX Integer32 (0..32)
			MAX-ACCESS read-write
			STATUS current
			DESCRIPTION
				"The number of GE ports."
			::= { onuCapabilityEntry 8 }

		
		onuCapE1PortNum OBJECT-TYPE
			SYNTAX Integer32 (0..8)
			MAX-ACCESS read-write
			STATUS current
			DESCRIPTION
				"The number of E1 ports."
			::= { onuCapabilityEntry 9 }

		
		onuCapT1PortNum OBJECT-TYPE
			SYNTAX Integer32 (0..8)
			MAX-ACCESS read-write
			STATUS current
			DESCRIPTION
				"The number of T1 ports."
			::= { onuCapabilityEntry 10 }

		
		onuCapMoCAPortNum OBJECT-TYPE
			SYNTAX Integer32 (0..8)
			MAX-ACCESS read-write
			STATUS current
			DESCRIPTION
				"The number of MoCA ports."
			::= { onuCapabilityEntry 11 }

		
		onuCapEOCPortNum OBJECT-TYPE
			SYNTAX Integer32 (0..8)
			MAX-ACCESS read-write
			STATUS current
			DESCRIPTION
				"The number of EOC ports."
			::= { onuCapabilityEntry 12 }

		
		onuCapWiFiPortNum OBJECT-TYPE
			SYNTAX Integer32 (0..8)
			MAX-ACCESS read-write
			STATUS current
			DESCRIPTION
				"The number of WiFi ports."
			::= { onuCapabilityEntry 13 }

		
		onuCapCATVPortNum OBJECT-TYPE
			SYNTAX Integer32 (0..2)
			MAX-ACCESS read-write
			STATUS current
			DESCRIPTION
				"The number of CATV ports."
			::= { onuCapabilityEntry 14 }

		
		onuCapClock1588PortNum OBJECT-TYPE
			SYNTAX Integer32 (0..2)
			MAX-ACCESS read-write
			STATUS current
			DESCRIPTION
				"The number of 1588 clock ports."
			::= { onuCapabilityEntry 15 }

		
		onuCapRSPortNum OBJECT-TYPE
			SYNTAX Integer32 (0..8)
			MAX-ACCESS read-write
			STATUS current
			DESCRIPTION
				"The number of RS ports."
			::= { onuCapabilityEntry 16 }

		
		onuCapADSLPortNum OBJECT-TYPE
			SYNTAX Integer32 (0..2)
			MAX-ACCESS read-write
			STATUS current
			DESCRIPTION
				"The number of ADSL ports."
			::= { onuCapabilityEntry 17 }

		
		onuCapVDSLPortNum OBJECT-TYPE
			SYNTAX Integer32 (0..2)
			MAX-ACCESS read-write
			STATUS current
			DESCRIPTION
				"The number of VDSL ports."
			::= { onuCapabilityEntry 18 }

		
		onuCapUSBPortNum OBJECT-TYPE
			SYNTAX Integer32 (0..2)
			MAX-ACCESS read-write
			STATUS current
			DESCRIPTION
				"The number of USB ports."
			::= { onuCapabilityEntry 19 }

		
		onuCapWanPortNum OBJECT-TYPE
			SYNTAX Integer32 (0..2)
			MAX-ACCESS read-write
			STATUS current
			DESCRIPTION
				"Description."
			::= { onuCapabilityEntry 20 }

		
		onuCapUser1Type OBJECT-TYPE
			SYNTAX Integer32
			MAX-ACCESS read-write
			STATUS current
			DESCRIPTION
				"The type of user-defined port 1."
			::= { onuCapabilityEntry 21 }

		
		onuCapUser1Num OBJECT-TYPE
			SYNTAX Integer32 (0..8)
			MAX-ACCESS read-write
			STATUS current
			DESCRIPTION
				"The number of user-defined port 1."
			::= { onuCapabilityEntry 22 }

		
		onuCapUser2Type OBJECT-TYPE
			SYNTAX Integer32
			MAX-ACCESS read-write
			STATUS current
			DESCRIPTION
				"The type of user-defined port 2."
			::= { onuCapabilityEntry 23 }

		
		onuCapUser2Num OBJECT-TYPE
			SYNTAX Integer32 (0..8)
			MAX-ACCESS read-write
			STATUS current
			DESCRIPTION
				"The number of user-defined port 2."
			::= { onuCapabilityEntry 24 }

		
		onuCapOnuType OBJECT-TYPE
			SYNTAX Integer32
			MAX-ACCESS read-only
			STATUS current
			DESCRIPTION
				"The onu type.
				Note: The value is '0' or '0xffff' when the profile is not created as onu type."
			::= { onuCapabilityEntry 25 }

		
		onuCapIsBound OBJECT-TYPE
			SYNTAX INTEGER
				{
				bound(1),
				notbound(2)
				}
			MAX-ACCESS read-only
			STATUS current
			DESCRIPTION
				"The profile is bound or not."
			::= { onuCapabilityEntry 26 }

		
		onuCapProfileStatusType OBJECT-TYPE
			SYNTAX INTEGER
				{
				dynamic(1),
				static(2)
				}
			MAX-ACCESS read-only
			STATUS current
			DESCRIPTION
				"The profile is configured by the user or auto-generated."
			::= { onuCapabilityEntry 27 }

		
		onuTrap OBJECT IDENTIFIER ::= { onuManage 5 }

		
		onuTrapObjects OBJECT IDENTIFIER ::= { onuTrap 1 }

		
		onuNewIfunit OBJECT-TYPE
			SYNTAX Integer32
			MAX-ACCESS read-write
			STATUS current
			DESCRIPTION
				"Description."
			::= { onuTrapObjects 1 }

		
		onuNewType OBJECT-TYPE
			SYNTAX Integer32
			MAX-ACCESS read-write
			STATUS current
			DESCRIPTION
				"Description."
			::= { onuTrapObjects 3 }

		
		onuNewCapIdx OBJECT-TYPE
			SYNTAX Integer32
			MAX-ACCESS read-write
			STATUS current
			DESCRIPTION
				"Description."
			::= { onuTrapObjects 4 }

		
		onuNewPhyID OBJECT-TYPE
			SYNTAX OCTET STRING
			MAX-ACCESS read-only
			STATUS current
			DESCRIPTION
				"Description."
			::= { onuTrapObjects 5 }

		
		onuNewPhyPwd OBJECT-TYPE
			SYNTAX OCTET STRING
			MAX-ACCESS read-write
			STATUS current
			DESCRIPTION
				"Description."
			::= { onuTrapObjects 6 }

		
		onuNewLoid OBJECT-TYPE
			SYNTAX OCTET STRING
			MAX-ACCESS read-write
			STATUS current
			DESCRIPTION
				"Description."
			::= { onuTrapObjects 7 }

		
		onuNewLogicalPwd OBJECT-TYPE
			SYNTAX OCTET STRING
			MAX-ACCESS read-write
			STATUS current
			DESCRIPTION
				"Description."
			::= { onuTrapObjects 8 }

		
		onuOldPhyID OBJECT-TYPE
			SYNTAX OCTET STRING
			MAX-ACCESS read-only
			STATUS current
			DESCRIPTION
				"Description."
			::= { onuTrapObjects 9 }

		
		onuOldType OBJECT-TYPE
			SYNTAX Integer32
			MAX-ACCESS read-only
			STATUS current
			DESCRIPTION
				"Description."
			::= { onuTrapObjects 10 }

		
		onuOldCapIdx OBJECT-TYPE
			SYNTAX Integer32
			MAX-ACCESS read-only
			STATUS current
			DESCRIPTION
				"Description."
			::= { onuTrapObjects 11 }

		
		onuAuth NOTIFICATION-TYPE
			OBJECTS { onuAuthIfindex, onuAuthOnuId, onuAuthPonType, onuAuthPhyId, onuAuthPhyPassword, 
				onuAuthLoid, onuAuthLoidPassword, onuAuthOnuType, onuAuthCapIdx, onuAuthAuthMode
				 }
			STATUS current
			DESCRIPTION 
				"Description."
			::= { onuTrap 2 }

		
		onuUnauth NOTIFICATION-TYPE
			OBJECTS { onuAuthIfindex, onuAuthOnuId, onuAuthPonType }
			STATUS current
			DESCRIPTION 
				"Description."
			::= { onuTrap 3 }

		
		illegalOnu NOTIFICATION-TYPE
			OBJECTS { onuAuthIfindex, onuAuthOnuId, onuAuthPonType }
			STATUS current
			DESCRIPTION 
				"Description."
			::= { onuTrap 4 }

		
		onuTypeErr NOTIFICATION-TYPE
			OBJECTS { onuAuthIfindex, onuAuthOnuId, onuAuthPonType, onuAuthOnuType, onuAuthCapIdx, 
				onuNewType, onuNewCapIdx }
			STATUS current
			DESCRIPTION 
				"Description."
			::= { onuTrap 5 }

		
		onuReplaceOK NOTIFICATION-TYPE
			OBJECTS { onuAuthIfindex, onuAuthOnuId, onuAuthPonType, onuNewPhyID, onuOldPhyID
				 }
			STATUS current
			DESCRIPTION 
				"Description."
			::= { onuTrap 6 }

		
		onuReplaceTypeErr NOTIFICATION-TYPE
			OBJECTS { onuAuthIfindex, onuAuthOnuId, onuAuthPonType, onuAuthOnuType, onuAuthCapIdx, 
				onuNewPhyID }
			STATUS current
			DESCRIPTION 
				"Description."
			::= { onuTrap 7 }

		
		onuPhyidConflict NOTIFICATION-TYPE
			OBJECTS { onuAuthIfindex, onuAuthOnuId, onuAuthPonType, onuAuthAuthMode, onuNewIfunit, 
				onuNewPhyID }
			STATUS current
			DESCRIPTION 
				"Description."
			::= { onuTrap 8 }

		
		onuLoidConflict NOTIFICATION-TYPE
			OBJECTS { onuAuthIfindex, onuAuthOnuId, onuAuthPonType, onuAuthAuthMode, onuNewPhyID, 
				onuNewLoid, onuNewLogicalPwd }
			STATUS current
			DESCRIPTION 
				"Description."
			::= { onuTrap 9 }

		
		onuLossLink NOTIFICATION-TYPE
			OBJECTS { onuAuthIfindex, onuAuthOnuId, onuAuthPhyId, onuAuthOnuType }
			STATUS current
			DESCRIPTION 
				"Description."
			::= { onuTrap 10 }

		
		onuShutdown NOTIFICATION-TYPE
			OBJECTS { onuAuthIfindex, onuAuthOnuId, onuAuthPhyId, onuAuthOnuType }
			STATUS current
			DESCRIPTION 
				"Description."
			::= { onuTrap 11 }

		
		onuFlashBusy NOTIFICATION-TYPE
			OBJECTS { onuAuthIfindex, onuAuthOnuId, onuAuthPhyId, onuAuthOnuType }
			STATUS current
			DESCRIPTION 
				"Description."
			::= { onuTrap 12 }

		
		onuFlashOk NOTIFICATION-TYPE
			OBJECTS { onuAuthIfindex, onuAuthOnuId, onuAuthPhyId, onuAuthOnuType }
			STATUS current
			DESCRIPTION 
				"Description."
			::= { onuTrap 13 }

		
		onuOamTimeOut NOTIFICATION-TYPE
			OBJECTS { onuAuthIfindex, onuAuthOnuId, onuAuthPhyId, onuAuthOnuType }
			STATUS current
			DESCRIPTION 
				"Description."
			::= { onuTrap 14 }

		
		onuLinkFault NOTIFICATION-TYPE
			OBJECTS { onuAuthIfindex, onuAuthOnuId, onuAuthPhyId, onuAuthOnuType }
			STATUS current
			DESCRIPTION 
				"Description."
			::= { onuTrap 15 }

		
		onuIrradiatedLasing NOTIFICATION-TYPE
			OBJECTS { onuAuthIfindex, onuAuthOnuId, onuAuthPhyId, onuAuthOnuType }
			STATUS current
			DESCRIPTION 
				"Description."
			::= { onuTrap 16 }

		
		onuPonIfTable OBJECT-TYPE
			SYNTAX SEQUENCE OF OnuPonIfEntry
			MAX-ACCESS not-accessible
			STATUS current
			DESCRIPTION
				"Description."
			::= { onuManage 6 }

		
		onuPonIfEntry OBJECT-TYPE
			SYNTAX OnuPonIfEntry
			MAX-ACCESS not-accessible
			STATUS current
			DESCRIPTION
				"Description."
			INDEX { onuPonIfIndex }
			::= { onuPonIfTable 1 }

		
		OnuPonIfEntry ::=
			SEQUENCE { 
				onuPonIfIndex
					InterfaceIndex,
				onuPonIfRegOnuList
					OCTET STRING
			 }

		onuPonIfIndex OBJECT-TYPE
			SYNTAX InterfaceIndex
			MAX-ACCESS read-only
			STATUS current
			DESCRIPTION
				"The interface index."
			::= { onuPonIfEntry 1 }

		
		onuPonIfRegOnuList OBJECT-TYPE
			SYNTAX OCTET STRING
			MAX-ACCESS read-only
			STATUS current
			DESCRIPTION
				"Description."
			::= { onuPonIfEntry 2 }

		
	
	END

--
-- onuManage.mib
--
